-- monitore.in
GEPON-OLT-COMMON-MIB DEFINITIONS ::= BEGIN
 
IMPORTS
	ifIndex			
		FROM IF-MIB			
	enterprises, IpAddress, Integer32, Unsigned32, OBJECT-TYPE			
		FROM SNMPv2-SMI			
	MacAddress, RowStatus, TruthValue, TEXTUAL-CONVENTION, DateAndTime
		FROM SNMPv2-TC;
	
	
-- TEXTUAL-CONVENTIONS --
MyTC ::= TEXTUAL-CONVENTION
	STATUS current
	DESCRIPTION 
		"TC Description"
	SYNTAX Integer32

	
--  Node definitions
-- 
-- 1.3.6.1.4.1.5875
fiberhome OBJECT IDENTIFIER ::= { enterprises 5875 }


-- 1.3.6.1.4.1.5875.800
standard OBJECT IDENTIFIER ::= { fiberhome 800 }


-- 1.3.6.1.4.1.5875.800.3
oltData OBJECT IDENTIFIER ::= { standard 3 }


-- 1.3.6.1.4.1.5875.800.3.1
onuWhiteList OBJECT IDENTIFIER ::= { oltData 1 }


-- 1.3.6.1.4.1.5875.800.3.1.1
onuPhysicalwhiteListTable OBJECT-TYPE
	SYNTAX SEQUENCE OF OnuPhysicalwhiteListEntry
	MAX-ACCESS not-accessible
	STATUS current
	DESCRIPTION
		"Description"
	::= { onuWhiteList 1 }


-- 1.3.6.1.4.1.5875.800.3.1.1.1
onuPhysicalwhiteListEntry OBJECT-TYPE
	SYNTAX OnuPhysicalwhiteListEntry
	MAX-ACCESS not-accessible
	STATUS current
	DESCRIPTION
		"Row Description"
	INDEX { onuAuthNo1 }
	::= { onuPhysicalwhiteListTable 1 }


OnuPhysicalwhiteListEntry ::=
	SEQUENCE { 
		onuAuthNo1
			Unsigned32,
		onuSlotForPhysical
			Integer32,
		onuPonForPhysical
			Integer32,
		onuMacForPhysical
			OCTET STRING,
		actionForPhysical
			INTEGER
	 }

-- 1.3.6.1.4.1.5875.800.3.1.1.1.1
onuAuthNo1 OBJECT-TYPE
	SYNTAX Unsigned32
	MAX-ACCESS read-only
	STATUS current
	DESCRIPTION
		"Column Description"
	::= { onuPhysicalwhiteListEntry 1 }


-- 1.3.6.1.4.1.5875.800.3.1.1.1.2
onuSlotForPhysical OBJECT-TYPE
	SYNTAX Integer32 (-2147483648..2147483647)
	MAX-ACCESS read-write
	STATUS current
	DESCRIPTION
		"Column Description"
	::= { onuPhysicalwhiteListEntry 2 }


-- 1.3.6.1.4.1.5875.800.3.1.1.1.3
onuPonForPhysical OBJECT-TYPE
	SYNTAX Integer32 (-2147483648..2147483647)
	MAX-ACCESS read-write
	STATUS current
	DESCRIPTION
		"Column Description"
	::= { onuPhysicalwhiteListEntry 3 }


-- 1.3.6.1.4.1.5875.800.3.1.1.1.4
onuMacForPhysical OBJECT-TYPE
	SYNTAX OCTET STRING
	MAX-ACCESS read-write
	STATUS current
	DESCRIPTION
		"Column Description"
	::= { onuPhysicalwhiteListEntry 4 }


-- 1.3.6.1.4.1.5875.800.3.1.1.1.5
actionForPhysical OBJECT-TYPE
	SYNTAX INTEGER
		{
		active(1),
		create(4),
		destroy(6)
		}
	MAX-ACCESS read-create
	STATUS current
	DESCRIPTION
		"4-create
		6-destroy"
	::= { onuPhysicalwhiteListEntry 5 }


-- 1.3.6.1.4.1.5875.800.3.1.2
onuLogicWhiteListTable OBJECT-TYPE
	SYNTAX SEQUENCE OF OnuLogicWhiteListEntry
	MAX-ACCESS not-accessible
	STATUS current
	DESCRIPTION
		"Description"
	::= { onuWhiteList 2 }


-- 1.3.6.1.4.1.5875.800.3.1.2.1
onuLogicWhiteListEntry OBJECT-TYPE
	SYNTAX OnuLogicWhiteListEntry
	MAX-ACCESS not-accessible
	STATUS current
	DESCRIPTION
		"Row Description"
	INDEX { onuAuthNo2 }
	::= { onuLogicWhiteListTable 1 }


OnuLogicWhiteListEntry ::=
	SEQUENCE { 
		onuAuthNo2
			Unsigned32,
		onuSlotForLogic
			Integer32,
		onuPonForLogic
			Integer32,
		onuSnForLogic
			OCTET STRING,
		onuSnPasswordForLogic
			OCTET STRING,
		actionForLogic
			INTEGER
	 }

-- 1.3.6.1.4.1.5875.800.3.1.2.1.1
onuAuthNo2 OBJECT-TYPE
	SYNTAX Unsigned32
	MAX-ACCESS read-only
	STATUS current
	DESCRIPTION
		"Column Description"
	::= { onuLogicWhiteListEntry 1 }


-- 1.3.6.1.4.1.5875.800.3.1.2.1.2
onuSlotForLogic OBJECT-TYPE
	SYNTAX Integer32
	MAX-ACCESS read-write
	STATUS current
	DESCRIPTION
		"Column Description"
	::= { onuLogicWhiteListEntry 2 }


-- 1.3.6.1.4.1.5875.800.3.1.2.1.3
onuPonForLogic OBJECT-TYPE
	SYNTAX Integer32
	MAX-ACCESS read-write
	STATUS current
	DESCRIPTION
		"Column Description"
	::= { onuLogicWhiteListEntry 3 }


-- 1.3.6.1.4.1.5875.800.3.1.2.1.4
onuSnForLogic OBJECT-TYPE
	SYNTAX OCTET STRING
	MAX-ACCESS read-write
	STATUS current
	DESCRIPTION
		"Column Description"
	::= { onuLogicWhiteListEntry 4 }


-- 1.3.6.1.4.1.5875.800.3.1.2.1.5
onuSnPasswordForLogic OBJECT-TYPE
	SYNTAX OCTET STRING
	MAX-ACCESS read-write
	STATUS current
	DESCRIPTION
		"Description"
	::= { onuLogicWhiteListEntry 5 }


-- 1.3.6.1.4.1.5875.800.3.1.2.1.6
actionForLogic OBJECT-TYPE
	SYNTAX INTEGER
		{
		active(1),
		create(4),
		destroy(6)
		}
	MAX-ACCESS read-create
	STATUS current
	DESCRIPTION
		"4-create
		6-destroy"
	::= { onuLogicWhiteListEntry 6 }


-- 1.3.6.1.4.1.5875.800.3.1.3
applyCommand OBJECT-TYPE
	SYNTAX Integer32 (-2147483648..2147483647)
	MAX-ACCESS read-write
	STATUS current
	DESCRIPTION
		"apply sn-whitelist or mac-whitelist to service card"
	::= { onuWhiteList 3 }


-- 1.3.6.1.4.1.5875.800.3.1.4
onuMacListFor5516Table OBJECT-TYPE
	SYNTAX SEQUENCE OF OnuMacListFor5516Entry
	MAX-ACCESS not-accessible
	STATUS current
	DESCRIPTION
		"Description"
	::= { onuWhiteList 4 }


-- 1.3.6.1.4.1.5875.800.3.1.4.1
onuMacListFor5516Entry OBJECT-TYPE
	SYNTAX OnuMacListFor5516Entry
	MAX-ACCESS not-accessible
	STATUS current
	DESCRIPTION
		"Row Description"
	INDEX { macListId }
	::= { onuMacListFor5516Table 1 }


OnuMacListFor5516Entry ::=
	SEQUENCE { 
		macListId
			Integer32,
		slotNoForMacList
			Integer32,
		ponNoForMacList
			Integer32,
		onuNoForMacList
			Integer32,
		onuTypeForMacList
			Integer32,
		macForMacList
			MacAddress,
		passwordForMacList
			OCTET STRING,
		actionForMacList
			RowStatus
	 }

-- 1.3.6.1.4.1.5875.800.3.1.4.1.1
macListId OBJECT-TYPE
	SYNTAX Integer32
	MAX-ACCESS read-only
	STATUS current
	DESCRIPTION
		"Column Description"
	::= { onuMacListFor5516Entry 1 }


-- 1.3.6.1.4.1.5875.800.3.1.4.1.2
slotNoForMacList OBJECT-TYPE
	SYNTAX Integer32 (-2147483648..2147483647)
	MAX-ACCESS read-write
	STATUS current
	DESCRIPTION
		"Column Description"
	::= { onuMacListFor5516Entry 2 }


-- 1.3.6.1.4.1.5875.800.3.1.4.1.3
ponNoForMacList OBJECT-TYPE
	SYNTAX Integer32 (-2147483648..2147483647)
	MAX-ACCESS read-write
	STATUS current
	DESCRIPTION
		"Column Description"
	::= { onuMacListFor5516Entry 3 }


-- 1.3.6.1.4.1.5875.800.3.1.4.1.4
onuNoForMacList OBJECT-TYPE
	SYNTAX Integer32 (-2147483648..2147483647)
	MAX-ACCESS read-write
	STATUS current
	DESCRIPTION
		"Column Description"
	::= { onuMacListFor5516Entry 4 }


-- 1.3.6.1.4.1.5875.800.3.1.4.1.5
onuTypeForMacList OBJECT-TYPE
	SYNTAX Integer32 (-2147483648..2147483647)
	MAX-ACCESS read-write
	STATUS current
	DESCRIPTION
		"Column Description"
	::= { onuMacListFor5516Entry 5 }


-- 1.3.6.1.4.1.5875.800.3.1.4.1.6
macForMacList OBJECT-TYPE
	SYNTAX MacAddress (SIZE (6))
	MAX-ACCESS read-write
	STATUS current
	DESCRIPTION
		"Column Description"
	::= { onuMacListFor5516Entry 6 }


-- 1.3.6.1.4.1.5875.800.3.1.4.1.7
passwordForMacList OBJECT-TYPE
	SYNTAX OCTET STRING
	MAX-ACCESS read-write
	STATUS current
	DESCRIPTION
		"Column Description"
	::= { onuMacListFor5516Entry 7 }


-- 1.3.6.1.4.1.5875.800.3.1.4.1.8
actionForMacList OBJECT-TYPE
	SYNTAX RowStatus
		{
		active(1),
		notInService(2),
		notReady(3),
		createAndGo(4),
		createAndWait(5),
		destroy(6)
		}
	MAX-ACCESS read-create
	STATUS current
	DESCRIPTION
		"Column Description"
	::= { onuMacListFor5516Entry 8 }


-- 1.3.6.1.4.1.5875.800.3.1.5
onuSnListFor5516Table OBJECT-TYPE
	SYNTAX SEQUENCE OF OnuSnListFor5516Entry
	MAX-ACCESS not-accessible
	STATUS current
	DESCRIPTION
		"Description"
	::= { onuWhiteList 5 }


-- 1.3.6.1.4.1.5875.800.3.1.5.1
onuSnListFor5516Entry OBJECT-TYPE
	SYNTAX OnuSnListFor5516Entry
	MAX-ACCESS not-accessible
	STATUS current
	DESCRIPTION
		"Row Description"
	INDEX { snListId }
	::= { onuSnListFor5516Table 1 }


OnuSnListFor5516Entry ::=
	SEQUENCE { 
		snListId
			Integer32,
		slotNoForSnList
			Integer32,
		ponNoForSnList
			Integer32,
		onuNoForSnList
			Integer32,
		onuTypeForSnList
			Integer32,
		snForSnList
			OCTET STRING,
		passwordForSnList
			OCTET STRING,
		actionForSnList
			RowStatus
	 }

-- 1.3.6.1.4.1.5875.800.3.1.5.1.1
snListId OBJECT-TYPE
	SYNTAX Integer32
	MAX-ACCESS read-only
	STATUS current
	DESCRIPTION
		"Column Description"
	::= { onuSnListFor5516Entry 1 }


-- 1.3.6.1.4.1.5875.800.3.1.5.1.2
slotNoForSnList OBJECT-TYPE
	SYNTAX Integer32
	MAX-ACCESS read-write
	STATUS current
	DESCRIPTION
		"Column Description"
	::= { onuSnListFor5516Entry 2 }


-- 1.3.6.1.4.1.5875.800.3.1.5.1.3
ponNoForSnList OBJECT-TYPE
	SYNTAX Integer32
	MAX-ACCESS read-write
	STATUS current
	DESCRIPTION
		"Column Description"
	::= { onuSnListFor5516Entry 3 }


-- 1.3.6.1.4.1.5875.800.3.1.5.1.4
onuNoForSnList OBJECT-TYPE
	SYNTAX Integer32
	MAX-ACCESS read-write
	STATUS current
	DESCRIPTION
		"Column Description"
	::= { onuSnListFor5516Entry 4 }


-- 1.3.6.1.4.1.5875.800.3.1.5.1.5
onuTypeForSnList OBJECT-TYPE
	SYNTAX Integer32
	MAX-ACCESS read-write
	STATUS current
	DESCRIPTION
		"Column Description"
	::= { onuSnListFor5516Entry 5 }


-- 1.3.6.1.4.1.5875.800.3.1.5.1.6
snForSnList OBJECT-TYPE
	SYNTAX OCTET STRING
	MAX-ACCESS read-write
	STATUS current
	DESCRIPTION
		"Column Description"
	::= { onuSnListFor5516Entry 6 }


-- 1.3.6.1.4.1.5875.800.3.1.5.1.7
passwordForSnList OBJECT-TYPE
	SYNTAX OCTET STRING
	MAX-ACCESS read-write
	STATUS current
	DESCRIPTION
		"Column Description"
	::= { onuSnListFor5516Entry 7 }


-- 1.3.6.1.4.1.5875.800.3.1.5.1.8
actionForSnList OBJECT-TYPE
	SYNTAX RowStatus
		{
		active(1),
		notInService(2),
		notReady(3),
		createAndGo(4),
		createAndWait(5),
		destroy(6)
		}
	MAX-ACCESS read-create
	STATUS current
	DESCRIPTION
		"Column Description"
	::= { onuSnListFor5516Entry 8 }


-- 1.3.6.1.4.1.5875.800.3.2
interfaceEnable OBJECT IDENTIFIER ::= { oltData 2 }


-- 1.3.6.1.4.1.5875.800.3.2.1
voicePortEnableTable OBJECT-TYPE
	SYNTAX SEQUENCE OF VoicePortEnableEntry
	MAX-ACCESS not-accessible
	STATUS current
	DESCRIPTION
		"Description"
	::= { interfaceEnable 1 }


-- 1.3.6.1.4.1.5875.800.3.2.1.1
voicePortEnableEntry OBJECT-TYPE
	SYNTAX VoicePortEnableEntry
	MAX-ACCESS not-accessible
	STATUS current
	DESCRIPTION
		"Row Description"
	INDEX { potsIndex }
	::= { voicePortEnableTable 1 }


VoicePortEnableEntry ::=
	SEQUENCE { 
		potsPortEnable
			INTEGER
	 }

-- 1.3.6.1.4.1.5875.800.3.2.1.1.2
potsPortEnable OBJECT-TYPE
	SYNTAX INTEGER
		{
		enable(1),
		disable(0)
		}
	MAX-ACCESS read-write
	STATUS current
	DESCRIPTION
		"0-disable
		1-enable"
	::= { voicePortEnableEntry 2 }


-- 1.3.6.1.4.1.5875.800.3.2.2
dataPortEnableTable OBJECT-TYPE
	SYNTAX SEQUENCE OF DataPortEnableEntry
	MAX-ACCESS not-accessible
	STATUS current
	DESCRIPTION
		"Description"
	::= { interfaceEnable 2 }


-- 1.3.6.1.4.1.5875.800.3.2.2.1
dataPortEnableEntry OBJECT-TYPE
	SYNTAX DataPortEnableEntry
	MAX-ACCESS not-accessible
	STATUS current
	DESCRIPTION
		"Row Description"
	INDEX { portIndex }
	::= { dataPortEnableTable 1 }


DataPortEnableEntry ::=
	SEQUENCE { 
		dataPortEnable
			INTEGER
	 }

-- 1.3.6.1.4.1.5875.800.3.2.2.1.2
dataPortEnable OBJECT-TYPE
	SYNTAX INTEGER
		{
		enable(1),
		disable(0)
		}
	MAX-ACCESS read-write
	STATUS current
	DESCRIPTION
		"0-disable
		1-enable"
	::= { dataPortEnableEntry 2 }


-- 1.3.6.1.4.1.5875.800.3.2.3
oltPonEnableTable OBJECT-TYPE
	SYNTAX SEQUENCE OF OltPonEnableEntry
	MAX-ACCESS not-accessible
	STATUS current
	DESCRIPTION
		"Description"
	::= { interfaceEnable 3 }


-- 1.3.6.1.4.1.5875.800.3.2.3.1
oltPonEnableEntry OBJECT-TYPE
	SYNTAX OltPonEnableEntry
	MAX-ACCESS not-accessible
	STATUS current
	DESCRIPTION
		"Row Description"
	INDEX { ponIndex }
	::= { oltPonEnableTable 1 }


OltPonEnableEntry ::=
	SEQUENCE { 
		oltPonEnable
			INTEGER
	 }

-- 1.3.6.1.4.1.5875.800.3.2.3.1.1
oltPonEnable OBJECT-TYPE
	SYNTAX INTEGER
		{
		enable(1),
		disable(0)
		}
	MAX-ACCESS read-write
	STATUS current
	DESCRIPTION
		"Column Description:
		1:enable
		0:disable"
	::= { oltPonEnableEntry 1 }


-- 1.3.6.1.4.1.5875.800.3.3
onuPortConfig OBJECT IDENTIFIER ::= { oltData 3 }


-- 1.3.6.1.4.1.5875.800.3.3.1
bandwidthProfileTable OBJECT-TYPE
	SYNTAX SEQUENCE OF BandwidthProfileEntry
	MAX-ACCESS not-accessible
	STATUS current
	DESCRIPTION
		"Description"
	::= { onuPortConfig 1 }


-- 1.3.6.1.4.1.5875.800.3.3.1.1
bandwidthProfileEntry OBJECT-TYPE
	SYNTAX BandwidthProfileEntry
	MAX-ACCESS not-accessible
	STATUS current
	DESCRIPTION
		"Row Description"
	INDEX { bandwidthProfileId }
	::= { bandwidthProfileTable 1 }


BandwidthProfileEntry ::=
	SEQUENCE { 
		bandwidthProfileId
			Integer32,
		bandwidthProfileName
			OCTET STRING,
		upMinRate
			Integer32,
		upMaxRate
			Integer32,
		downMinRate
			Integer32,
		downMaxRate
			Integer32,
		fixedRate
			Integer32,
		bandwidthProfileAction
			INTEGER
	 }

-- 1.3.6.1.4.1.5875.800.3.3.1.1.1
bandwidthProfileId OBJECT-TYPE
	SYNTAX Integer32 (-2147483648..2147483647)
	MAX-ACCESS read-only
	STATUS current
	DESCRIPTION
		"Column Description"
	::= { bandwidthProfileEntry 1 }


-- 1.3.6.1.4.1.5875.800.3.3.1.1.2
bandwidthProfileName OBJECT-TYPE
	SYNTAX OCTET STRING
	MAX-ACCESS read-write
	STATUS current
	DESCRIPTION
		"Column Description"
	::= { bandwidthProfileEntry 2 }


-- 1.3.6.1.4.1.5875.800.3.3.1.1.3
upMinRate OBJECT-TYPE
	SYNTAX Integer32 (-2147483648..2147483647)
	MAX-ACCESS read-write
	STATUS current
	DESCRIPTION
		"Column Description"
	::= { bandwidthProfileEntry 3 }


-- 1.3.6.1.4.1.5875.800.3.3.1.1.4
upMaxRate OBJECT-TYPE
	SYNTAX Integer32 (-2147483648..2147483647)
	MAX-ACCESS read-write
	STATUS current
	DESCRIPTION
		"Column Description"
	::= { bandwidthProfileEntry 4 }


-- 1.3.6.1.4.1.5875.800.3.3.1.1.5
downMinRate OBJECT-TYPE
	SYNTAX Integer32 (-2147483648..2147483647)
	MAX-ACCESS read-write
	STATUS current
	DESCRIPTION
		"Column Description"
	::= { bandwidthProfileEntry 5 }


-- 1.3.6.1.4.1.5875.800.3.3.1.1.6
downMaxRate OBJECT-TYPE
	SYNTAX Integer32 (-2147483648..2147483647)
	MAX-ACCESS read-write
	STATUS current
	DESCRIPTION
		"Column Description"
	::= { bandwidthProfileEntry 6 }


-- 1.3.6.1.4.1.5875.800.3.3.1.1.7
fixedRate OBJECT-TYPE
	SYNTAX Integer32 (-2147483648..2147483647)
	MAX-ACCESS read-write
	STATUS current
	DESCRIPTION
		"Column Description"
	::= { bandwidthProfileEntry 7 }


-- 1.3.6.1.4.1.5875.800.3.3.1.1.12
bandwidthProfileAction OBJECT-TYPE
	SYNTAX INTEGER
		{
		active(1),
		create(4),
		destroy(6),
		modify(7)
		}
	MAX-ACCESS read-create
	STATUS current
	DESCRIPTION
		"1-active
		4-create
		6-destroy
		7-modify"
	::= { bandwidthProfileEntry 12 }


-- 1.3.6.1.4.1.5875.800.3.3.2
attachPortBandwidthProfileTable OBJECT-TYPE
	SYNTAX SEQUENCE OF AttachPortBandwidthProfileEntry
	MAX-ACCESS not-accessible
	STATUS current
	DESCRIPTION
		"Description"
	::= { onuPortConfig 2 }


-- 1.3.6.1.4.1.5875.800.3.3.2.1
attachPortBandwidthProfileEntry OBJECT-TYPE
	SYNTAX AttachPortBandwidthProfileEntry
	MAX-ACCESS not-accessible
	STATUS current
	DESCRIPTION
		"Row Description"
	INDEX { fttbIfIndex }
	::= { attachPortBandwidthProfileTable 1 }


AttachPortBandwidthProfileEntry ::=
	SEQUENCE { 
		fttbIfIndex
			Unsigned32,
		attachBandwidthProfileId
			Integer32,
		attachBandwidthProfileName
			OCTET STRING,
		setDefaultBandwidthProfileAction  
		  Integer32
	 }

-- 1.3.6.1.4.1.5875.800.3.3.2.1.1
fttbIfIndex OBJECT-TYPE
	SYNTAX Unsigned32
	MAX-ACCESS read-only
	STATUS current
	DESCRIPTION
		"Description"
	::= { attachPortBandwidthProfileEntry 1 }


-- 1.3.6.1.4.1.5875.800.3.3.2.1.2
attachBandwidthProfileId OBJECT-TYPE
	SYNTAX Integer32 (-2147483648..2147483647)
	MAX-ACCESS read-write
	STATUS current
	DESCRIPTION
		"Column Description"
	::= { attachPortBandwidthProfileEntry 2 }


-- 1.3.6.1.4.1.5875.800.3.3.2.1.4
attachBandwidthProfileName OBJECT-TYPE
	SYNTAX OCTET STRING
	MAX-ACCESS read-write
	STATUS current
	DESCRIPTION
		"Description"
	::= { attachPortBandwidthProfileEntry 4 }

setDefaultBandwidthProfileAction	OBJECT-TYPE	
	SYNTAX			Integer32  ( 0 .. 1  ) 
	MAX-ACCESS		read-write
	STATUS			current
	DESCRIPTION		"Description"
	::=  {  attachPortBandwidthProfileEntry  5  }			


-- 1.3.6.1.4.1.5875.800.3.3.3
portAttributeProfileTable OBJECT-TYPE
	SYNTAX SEQUENCE OF PortAttributeProfileEntry
	MAX-ACCESS not-accessible
	STATUS current
	DESCRIPTION
		"Description"
	::= { onuPortConfig 3 }


-- 1.3.6.1.4.1.5875.800.3.3.3.1
portAttributeProfileEntry OBJECT-TYPE
	SYNTAX PortAttributeProfileEntry
	MAX-ACCESS not-accessible
	STATUS current
	DESCRIPTION
		"Row Description"
	INDEX { portAttributeProfileId }
	::= { portAttributeProfileTable 1 }


PortAttributeProfileEntry ::=
	SEQUENCE { 
		portAttributeProfileId
			Integer32,
		portAttributeProfileName
			OCTET STRING,
		autoNegotiation
			INTEGER,
		speed
			Integer32,
		duplex
			INTEGER,
		flowControl
			INTEGER,
		portAttributeProfileAction
			INTEGER
	 }

-- 1.3.6.1.4.1.5875.800.3.3.3.1.1
portAttributeProfileId OBJECT-TYPE
	SYNTAX Integer32
	MAX-ACCESS read-only
	STATUS current
	DESCRIPTION
		"Column Description"
	::= { portAttributeProfileEntry 1 }


-- 1.3.6.1.4.1.5875.800.3.3.3.1.2
portAttributeProfileName OBJECT-TYPE
	SYNTAX OCTET STRING
	MAX-ACCESS read-write
	STATUS current
	DESCRIPTION
		"Column Description"
	::= { portAttributeProfileEntry 2 }


-- 1.3.6.1.4.1.5875.800.3.3.3.1.3
autoNegotiation OBJECT-TYPE
	SYNTAX INTEGER
		{
		enable(1),
		disable(0),
		disableFor5116(2)
		}
	MAX-ACCESS read-write
	STATUS current
	DESCRIPTION
		"Column Description: 
		5516:
		1:enable
		0:disable 
		5116:
		1:enable
		2:disableFor5116
		"
	::= { portAttributeProfileEntry 3 }


-- 1.3.6.1.4.1.5875.800.3.3.3.1.4
speed OBJECT-TYPE
	SYNTAX Integer32 (0..2)
	MAX-ACCESS read-write
	STATUS current
	DESCRIPTION
		"Column Description:
		0:10M
		1:100M
		2:1000M"
	::= { portAttributeProfileEntry 4 }


-- 1.3.6.1.4.1.5875.800.3.3.3.1.5
duplex OBJECT-TYPE
	SYNTAX INTEGER
		{
		enable(1),
		disable(0)
		}
	MAX-ACCESS read-write
	STATUS current
	DESCRIPTION
		"Column Description:
		1:enable
		0:disable"
	::= { portAttributeProfileEntry 5 }


-- 1.3.6.1.4.1.5875.800.3.3.3.1.6
flowControl OBJECT-TYPE
	SYNTAX INTEGER
		{
		enable(1),
		disable(0)
		}
	MAX-ACCESS read-write
	STATUS current
	DESCRIPTION
		"Column Description:
		1:enable
		0:disable"
	::= { portAttributeProfileEntry 6 }


-- 1.3.6.1.4.1.5875.800.3.3.3.1.10
portAttributeProfileAction OBJECT-TYPE
	SYNTAX INTEGER
		{
		active(1),
		create(4),
		destroy(6),
		modify(7)
		}
	MAX-ACCESS read-create
	STATUS current
	DESCRIPTION
		"Column Description
		4:create
		6:destroy
		7:modify"
	::= { portAttributeProfileEntry 10 }


-- 1.3.6.1.4.1.5875.800.3.3.4
attachPortAttributeProfileTable OBJECT-TYPE
	SYNTAX SEQUENCE OF AttachPortAttributeProfileEntry
	MAX-ACCESS not-accessible
	STATUS current
	DESCRIPTION
		"Description"
	::= { onuPortConfig 4 }


-- 1.3.6.1.4.1.5875.800.3.3.4.1
attachPortAttributeProfileEntry OBJECT-TYPE
	SYNTAX AttachPortAttributeProfileEntry
	MAX-ACCESS not-accessible
	STATUS current
	DESCRIPTION
		"Row Description"
	INDEX { portIndex }
	::= { attachPortAttributeProfileTable 1 }


AttachPortAttributeProfileEntry ::=
	SEQUENCE { 
		attachPortAttributeProfileName
			OCTET STRING,
	  setDefaultPortAttributeProfileAction  
	    Integer32
	 }

-- 1.3.6.1.4.1.5875.800.3.3.4.1.1
attachPortAttributeProfileName OBJECT-TYPE
	SYNTAX OCTET STRING
	MAX-ACCESS read-write
	STATUS current
	DESCRIPTION
		"Column Description"
	::= { attachPortAttributeProfileEntry 1 }
	
setDefaultPortAttributeProfileAction	OBJECT-TYPE	
	SYNTAX			Integer32  ( 0 .. 1  ) 
	MAX-ACCESS		read-write
	STATUS			current
	DESCRIPTION		"Description"
	::=  {  attachPortAttributeProfileEntry  2  }			


-- 1.3.6.1.4.1.5875.800.3.3.10
getNextPortProfileId OBJECT IDENTIFIER ::= { onuPortConfig 10 }


-- 1.3.6.1.4.1.5875.800.3.3.10.1
getNextBandwidthProfileId OBJECT-TYPE
	SYNTAX Integer32
	MAX-ACCESS read-only
	STATUS current
	DESCRIPTION
		"Description"
	::= { getNextPortProfileId 1 }


-- 1.3.6.1.4.1.5875.800.3.3.10.2
getNextPortAttributeProfileId OBJECT-TYPE
	SYNTAX Integer32
	MAX-ACCESS read-only
	STATUS current
	DESCRIPTION
		"Description"
	::= { getNextPortProfileId 2 }


-- 1.3.6.1.4.1.5875.800.3.5
feServiceConfigure OBJECT IDENTIFIER ::= { oltData 5 }


-- 1.3.6.1.4.1.5875.800.3.5.1
feServiceCfgTable OBJECT-TYPE
	SYNTAX SEQUENCE OF FeServiceCfgEntry
	MAX-ACCESS not-accessible
	STATUS current
	DESCRIPTION
		"Description"
	::= { feServiceConfigure 1 }


-- 1.3.6.1.4.1.5875.800.3.5.1.1
feServiceCfgEntry OBJECT-TYPE
	SYNTAX FeServiceCfgEntry
	MAX-ACCESS not-accessible
	STATUS current
	DESCRIPTION
		"Row Description"
	INDEX { portIndex, serviceId }
	::= { feServiceCfgTable 1 }


FeServiceCfgEntry ::=
	SEQUENCE { 
		serviceId
			Integer32,
		serviceType
			Integer32,
		cvlanMode
			INTEGER,
		cvlan
			Integer32,
		cvlanCos
			Integer32,
		tvlan
			Integer32,
		tvlanCos
			Integer32,
		svlan
			Integer32,
		svlanCos
			Integer32,
		upMinBandWidth
			Integer32,
		upManBandWidth
			Integer32,
		dnBandWidth
			Integer32,
		serviceVlanName
			OCTET STRING,
		qinqProfileName
			OCTET STRING,
		feServiceCfgAction
			INTEGER
	 }

-- 1.3.6.1.4.1.5875.800.3.5.1.1.1
serviceId OBJECT-TYPE
	SYNTAX Integer32
	MAX-ACCESS read-only
	STATUS current
	DESCRIPTION
		"Column Description"
	::= { feServiceCfgEntry 1 }


-- 1.3.6.1.4.1.5875.800.3.5.1.1.2
serviceType OBJECT-TYPE
	SYNTAX Integer32 (0..1)
	MAX-ACCESS read-write
	STATUS current
	DESCRIPTION
		"Column Description:
		0:unicast
		1:mulitcast"
	::= { feServiceCfgEntry 2 }


-- 1.3.6.1.4.1.5875.800.3.5.1.1.3
cvlanMode OBJECT-TYPE
	SYNTAX INTEGER { tag(1), transparent(3) }
	MAX-ACCESS read-write
	STATUS current
	DESCRIPTION
		"Column Description:
		1:tag
		3:transparent"
	::= { feServiceCfgEntry 3 }


-- 1.3.6.1.4.1.5875.800.3.5.1.1.4
cvlan OBJECT-TYPE
	SYNTAX Integer32 (1..4085)
	MAX-ACCESS read-write
	STATUS current
	DESCRIPTION
		"Column Description:
		1~4085"
	::= { feServiceCfgEntry 4 }


-- 1.3.6.1.4.1.5875.800.3.5.1.1.5
cvlanCos OBJECT-TYPE
	SYNTAX Integer32 (0..7)
	MAX-ACCESS read-write
	STATUS current
	DESCRIPTION
		"Column Description:
		0~7"
	::= { feServiceCfgEntry 5 }


-- 1.3.6.1.4.1.5875.800.3.5.1.1.6
tvlan OBJECT-TYPE
	SYNTAX Integer32 (1..4085 | 65535)
	MAX-ACCESS read-write
	STATUS current
	DESCRIPTION
		"Column Description:
		1.value:1~4085
		2:65535   interpreter(off)"
	::= { feServiceCfgEntry 6 }


-- 1.3.6.1.4.1.5875.800.3.5.1.1.7
tvlanCos OBJECT-TYPE
	SYNTAX Integer32 (0..7 | 255)
	MAX-ACCESS read-write
	STATUS current
	DESCRIPTION
		"Column Description:
		value:0~7"
	::= { feServiceCfgEntry 7 }


-- 1.3.6.1.4.1.5875.800.3.5.1.1.8
svlan OBJECT-TYPE
	SYNTAX Integer32 (1..4085 | 65535)
	MAX-ACCESS read-write
	STATUS current
	DESCRIPTION
		"Column Description:
		1:value(1~4085)
		2:65535(QINQ off)"
	::= { feServiceCfgEntry 8 }


-- 1.3.6.1.4.1.5875.800.3.5.1.1.9
svlanCos OBJECT-TYPE
	SYNTAX Integer32 (0..7 | 255)
	MAX-ACCESS read-write
	STATUS current
	DESCRIPTION
		"Column Description:
		value:0~7"
	::= { feServiceCfgEntry 9 }


-- 1.3.6.1.4.1.5875.800.3.5.1.1.10
upMinBandWidth OBJECT-TYPE
	SYNTAX Integer32 (0..1000000)
	MAX-ACCESS read-write
	STATUS current
	DESCRIPTION
		"Column Description:
		value:0~1000000"
	::= { feServiceCfgEntry 10 }


-- 1.3.6.1.4.1.5875.800.3.5.1.1.11
upManBandWidth OBJECT-TYPE
	SYNTAX Integer32 (256..1000000)
	MAX-ACCESS read-write
	STATUS current
	DESCRIPTION
		"Column Description:
		value:256~1000000"
	::= { feServiceCfgEntry 11 }


-- 1.3.6.1.4.1.5875.800.3.5.1.1.12
dnBandWidth OBJECT-TYPE
	SYNTAX Integer32 (0..1000000)
	MAX-ACCESS read-write
	STATUS current
	DESCRIPTION
		"Column Description:
		value:0~1000000"
	::= { feServiceCfgEntry 12 }


-- 1.3.6.1.4.1.5875.800.3.5.1.1.15
serviceVlanName OBJECT-TYPE
	SYNTAX OCTET STRING
	MAX-ACCESS read-write
	STATUS current
	DESCRIPTION
		"Column Description"
	::= { feServiceCfgEntry 15 }


-- 1.3.6.1.4.1.5875.800.3.5.1.1.16
qinqProfileName OBJECT-TYPE
	SYNTAX OCTET STRING
	MAX-ACCESS read-write
	STATUS current
	DESCRIPTION
		"Column Description:
		if the qinq off, the value is meaningless"
	::= { feServiceCfgEntry 16 }


-- 1.3.6.1.4.1.5875.800.3.5.1.1.20
feServiceCfgAction OBJECT-TYPE
	SYNTAX INTEGER
		{
		active(1),
		create(4),
		destroy(6),
		modify(7)
		}
	MAX-ACCESS read-create
	STATUS current
	DESCRIPTION
		"Column Description:
		1:create(4)
		2:destroy(6)
		3:modify(7)"
	::= { feServiceCfgEntry 20 }


-- 1.3.6.1.4.1.5875.800.3.5.2
feServiceCfgIdTable OBJECT-TYPE
	SYNTAX SEQUENCE OF FeServiceCfgIdEntry
	MAX-ACCESS not-accessible
	STATUS current
	DESCRIPTION
		"Description"
	::= { feServiceConfigure 2 }


-- 1.3.6.1.4.1.5875.800.3.5.2.1
feServiceCfgIdEntry OBJECT-TYPE
	SYNTAX FeServiceCfgIdEntry
	MAX-ACCESS not-accessible
	STATUS current
	DESCRIPTION
		"Row Description"
	INDEX { portIndex }
	::= { feServiceCfgIdTable 1 }


FeServiceCfgIdEntry ::=
	SEQUENCE { 
		nextServiceId
			Integer32
	 }

-- 1.3.6.1.4.1.5875.800.3.5.2.1.1
nextServiceId OBJECT-TYPE
	SYNTAX Integer32
	MAX-ACCESS read-only
	STATUS current
	DESCRIPTION
		"Column Description"
	::= { feServiceCfgIdEntry 1 }


-- 1.3.6.1.4.1.5875.800.3.5.3
feServiceCfgApplyTable OBJECT-TYPE
	SYNTAX SEQUENCE OF FeServiceCfgApplyEntry
	MAX-ACCESS not-accessible
	STATUS current
	DESCRIPTION
		"Description"
	::= { feServiceConfigure 3 }


-- 1.3.6.1.4.1.5875.800.3.5.3.1
feServiceCfgApplyEntry OBJECT-TYPE
	SYNTAX FeServiceCfgApplyEntry
	MAX-ACCESS not-accessible
	STATUS current
	DESCRIPTION
		"Row Description"
	INDEX { portIndex }
	::= { feServiceCfgApplyTable 1 }


FeServiceCfgApplyEntry ::=
	SEQUENCE { 
		feServiceCfgApplyCommand
			TruthValue
	 }

-- 1.3.6.1.4.1.5875.800.3.5.3.1.1
feServiceCfgApplyCommand OBJECT-TYPE
	SYNTAX TruthValue
	MAX-ACCESS read-write
	STATUS current
	DESCRIPTION
		"Column Description"
	::= { feServiceCfgApplyEntry 1 }


-- 1.3.6.1.4.1.5875.800.3.7
qinq OBJECT IDENTIFIER ::= { oltData 7 }


-- 1.3.6.1.4.1.5875.800.3.7.2
attachQINQProfileTable OBJECT-TYPE
	SYNTAX SEQUENCE OF AttachQINQProfileEntry
	MAX-ACCESS not-accessible
	STATUS current
	DESCRIPTION
		"Description"
	::= { qinq 2 }


-- 1.3.6.1.4.1.5875.800.3.7.2.1
attachQINQProfileEntry OBJECT-TYPE
	SYNTAX AttachQINQProfileEntry
	MAX-ACCESS not-accessible
	STATUS current
	DESCRIPTION
		"Row Description"
	INDEX { attachQINQProfileName }
	::= { attachQINQProfileTable 1 }


AttachQINQProfileEntry ::=
	SEQUENCE { 
		attachQINQProfileId
			Integer32,
		attachQINQProfileName
			OCTET STRING,
		attachQINQSvlan
			Integer32,
		attachQINQTpid
			Integer32,
		attachQINQCos
			Integer32,
		attachQINQProfileAction
			INTEGER
	 }

-- 1.3.6.1.4.1.5875.800.3.7.2.1.1
attachQINQProfileId OBJECT-TYPE
	SYNTAX Integer32 (-2147483648..2147483647)
	MAX-ACCESS read-only
	STATUS current
	DESCRIPTION
		"Column Description"
	::= { attachQINQProfileEntry 1 }


-- 1.3.6.1.4.1.5875.800.3.7.2.1.2
attachQINQProfileName OBJECT-TYPE
	SYNTAX OCTET STRING
	MAX-ACCESS read-write
	STATUS current
	DESCRIPTION
		"Column Description"
	::= { attachQINQProfileEntry 2 }


-- 1.3.6.1.4.1.5875.800.3.7.2.1.3
attachQINQSvlan OBJECT-TYPE
	SYNTAX Integer32 (-2147483648..2147483647)
	MAX-ACCESS read-write
	STATUS current
	DESCRIPTION
		"Column Description"
	::= { attachQINQProfileEntry 3 }


-- 1.3.6.1.4.1.5875.800.3.7.2.1.4
attachQINQTpid OBJECT-TYPE
	SYNTAX Integer32 (-2147483648..2147483647)
	MAX-ACCESS read-write
	STATUS current
	DESCRIPTION
		"Column Description"
	::= { attachQINQProfileEntry 4 }


-- 1.3.6.1.4.1.5875.800.3.7.2.1.5
attachQINQCos OBJECT-TYPE
	SYNTAX Integer32 (-2147483648..2147483647)
	MAX-ACCESS read-write
	STATUS current
	DESCRIPTION
		"Column Description"
	::= { attachQINQProfileEntry 5 }


-- 1.3.6.1.4.1.5875.800.3.7.2.1.6
attachQINQProfileAction OBJECT-TYPE
	SYNTAX INTEGER
		{
		create(4),
		destroy(6)
		}
	MAX-ACCESS read-create
	STATUS current
	DESCRIPTION
		"4-create
		6-delete
		7-modify"
	::= { attachQINQProfileEntry 6 }


-- 1.3.6.1.4.1.5875.800.3.7.3
attchQinqProfileToOnuTable OBJECT-TYPE
	SYNTAX SEQUENCE OF AttchQinqProfileToOnuEntry
	MAX-ACCESS not-accessible
	STATUS current
	DESCRIPTION
		"Description"
	::= { qinq 3 }


-- 1.3.6.1.4.1.5875.800.3.7.3.1
attchQinqProfileToOnuEntry OBJECT-TYPE
	SYNTAX AttchQinqProfileToOnuEntry
	MAX-ACCESS not-accessible
	STATUS current
	DESCRIPTION
		"Row Description"
	INDEX { onuIndex }
	::= { attchQinqProfileToOnuTable 1 }


AttchQinqProfileToOnuEntry ::=
	SEQUENCE { 
		attchQinqProfileName
			OCTET STRING,
		qinqAttchAction
			Integer32,
		getOnuQinqProfileName
			OCTET STRING
	 }

-- 1.3.6.1.4.1.5875.800.3.7.3.1.1
attchQinqProfileName OBJECT-TYPE
	SYNTAX OCTET STRING
	MAX-ACCESS read-write
	STATUS current
	DESCRIPTION
		"Column Description"
	::= { attchQinqProfileToOnuEntry 1 }


-- 1.3.6.1.4.1.5875.800.3.7.3.1.2
qinqAttchAction OBJECT-TYPE
	SYNTAX Integer32 (0..1)
	MAX-ACCESS read-create
	STATUS current
	DESCRIPTION
		"Description:
		1:bind(1)
		2:unbind(0)"
	::= { attchQinqProfileToOnuEntry 2 }


-- 1.3.6.1.4.1.5875.800.3.7.3.1.3
getOnuQinqProfileName OBJECT-TYPE
	SYNTAX OCTET STRING
	MAX-ACCESS read-only
	STATUS current
	DESCRIPTION
		"Description"
	::= { attchQinqProfileToOnuEntry 3 }


-- 1.3.6.1.4.1.5875.800.3.7.4
qinqBandWidthCfgTable OBJECT-TYPE
	SYNTAX SEQUENCE OF QinqBandWidthCfgEntry
	MAX-ACCESS not-accessible
	STATUS current
	DESCRIPTION
		"Description"
	::= { qinq 4 }


-- 1.3.6.1.4.1.5875.800.3.7.4.1
qinqBandWidthCfgEntry OBJECT-TYPE
	SYNTAX QinqBandWidthCfgEntry
	MAX-ACCESS not-accessible
	STATUS current
	DESCRIPTION
		"Row Description"
	INDEX { onuIndex, onuQinqProfileName, qinqServiceId }
	::= { qinqBandWidthCfgTable 1 }


QinqBandWidthCfgEntry ::=
	SEQUENCE { 
		onuQinqProfileName
			OCTET STRING,
		qinqServiceId
			Integer32,
		usMinBandwidth
			Integer32,
		usMaxBandwidth
			Integer32,
		usBurstBandwidth
			Integer32,
		dsMinBandwidth
			Integer32,
		dsMaxBandwidth
			Integer32,
		dsBurstBandwidth
			Integer32,
		qinqBandwidthCfgAction
			Integer32
	 }

-- 1.3.6.1.4.1.5875.800.3.7.4.1.1
onuQinqProfileName OBJECT-TYPE
	SYNTAX OCTET STRING
	MAX-ACCESS read-only
	STATUS current
	DESCRIPTION
		"Column Description"
	::= { qinqBandWidthCfgEntry 1 }


-- 1.3.6.1.4.1.5875.800.3.7.4.1.2
qinqServiceId OBJECT-TYPE
	SYNTAX Integer32
	MAX-ACCESS read-only
	STATUS current
	DESCRIPTION
		"Column Description"
	::= { qinqBandWidthCfgEntry 2 }


-- 1.3.6.1.4.1.5875.800.3.7.4.1.3
usMinBandwidth OBJECT-TYPE
	SYNTAX Integer32
	MAX-ACCESS read-write
	STATUS current
	DESCRIPTION
		"Column Description"
	::= { qinqBandWidthCfgEntry 3 }


-- 1.3.6.1.4.1.5875.800.3.7.4.1.4
usMaxBandwidth OBJECT-TYPE
	SYNTAX Integer32
	MAX-ACCESS read-write
	STATUS current
	DESCRIPTION
		"Column Description"
	::= { qinqBandWidthCfgEntry 4 }


-- 1.3.6.1.4.1.5875.800.3.7.4.1.5
usBurstBandwidth OBJECT-TYPE
	SYNTAX Integer32
	MAX-ACCESS read-write
	STATUS current
	DESCRIPTION
		"Column Description"
	::= { qinqBandWidthCfgEntry 5 }


-- 1.3.6.1.4.1.5875.800.3.7.4.1.6
dsMinBandwidth OBJECT-TYPE
	SYNTAX Integer32
	MAX-ACCESS read-write
	STATUS current
	DESCRIPTION
		"Column Description"
	::= { qinqBandWidthCfgEntry 6 }


-- 1.3.6.1.4.1.5875.800.3.7.4.1.7
dsMaxBandwidth OBJECT-TYPE
	SYNTAX Integer32
	MAX-ACCESS read-write
	STATUS current
	DESCRIPTION
		"Column Description"
	::= { qinqBandWidthCfgEntry 7 }


-- 1.3.6.1.4.1.5875.800.3.7.4.1.8
dsBurstBandwidth OBJECT-TYPE
	SYNTAX Integer32 (-2147483648..2147483647)
	MAX-ACCESS read-write
	STATUS current
	DESCRIPTION
		"Column Description"
	::= { qinqBandWidthCfgEntry 8 }


-- 1.3.6.1.4.1.5875.800.3.7.4.1.20
qinqBandwidthCfgAction OBJECT-TYPE
	SYNTAX Integer32 (-2147483648..2147483647)
	MAX-ACCESS read-create
	STATUS current
	DESCRIPTION
		"Column Description"
	::= { qinqBandWidthCfgEntry 20 }


-- 1.3.6.1.4.1.5875.800.3.7.5
qinqBandwidthCfgApplyTable OBJECT-TYPE
	SYNTAX SEQUENCE OF QinqBandwidthCfgApplyEntry
	MAX-ACCESS not-accessible
	STATUS current
	DESCRIPTION
		"Description"
	::= { qinq 5 }


-- 1.3.6.1.4.1.5875.800.3.7.5.1
qinqBandwidthCfgApplyEntry OBJECT-TYPE
	SYNTAX QinqBandwidthCfgApplyEntry
	MAX-ACCESS not-accessible
	STATUS current
	DESCRIPTION
		"Row Description"
	INDEX { onuIndex }
	::= { qinqBandwidthCfgApplyTable 1 }


QinqBandwidthCfgApplyEntry ::=
	SEQUENCE { 
		qinqBandwidthCfgApply
			Integer32
	 }

-- 1.3.6.1.4.1.5875.800.3.7.5.1.1
qinqBandwidthCfgApply OBJECT-TYPE
	SYNTAX Integer32
	MAX-ACCESS read-write
	STATUS current
	DESCRIPTION
		"Column Description"
	::= { qinqBandwidthCfgApplyEntry 1 }


-- 1.3.6.1.4.1.5875.800.3.7.7
qinqDomainTable OBJECT-TYPE
	SYNTAX SEQUENCE OF QinqDomainEntry
	MAX-ACCESS not-accessible
	STATUS current
	DESCRIPTION
		"Description"
	::= { qinq 7 }


-- 1.3.6.1.4.1.5875.800.3.7.7.1
qinqDomainEntry OBJECT-TYPE
	SYNTAX QinqDomainEntry
	MAX-ACCESS not-accessible
	STATUS current
	DESCRIPTION
		"Row Description"
	INDEX { qinqDomainName }
	::= { qinqDomainTable 1 }


QinqDomainEntry ::=
	SEQUENCE { 
		qinqDomainName
			OCTET STRING,
		qinqDomainAction
			RowStatus,
		qinqDomainServiceNum
			Integer32,
		nextQinqDomainServiceId
			Integer32
	 }

-- 1.3.6.1.4.1.5875.800.3.7.7.1.1
qinqDomainName OBJECT-TYPE
	SYNTAX OCTET STRING
	MAX-ACCESS read-only
	STATUS current
	DESCRIPTION
		"Column Description"
	::= { qinqDomainEntry 1 }


-- 1.3.6.1.4.1.5875.800.3.7.7.1.4
qinqDomainAction OBJECT-TYPE
	SYNTAX RowStatus
	MAX-ACCESS read-create
	STATUS current
	DESCRIPTION
		"Column Description"
	::= { qinqDomainEntry 4 }


-- 1.3.6.1.4.1.5875.800.3.7.7.1.5
qinqDomainServiceNum OBJECT-TYPE
	SYNTAX Integer32
	MAX-ACCESS read-only
	STATUS current
	DESCRIPTION
		"Column Description"
	::= { qinqDomainEntry 5 }


-- 1.3.6.1.4.1.5875.800.3.7.7.1.6
nextQinqDomainServiceId OBJECT-TYPE
	SYNTAX Integer32
	MAX-ACCESS read-only
	STATUS current
	DESCRIPTION
		"Column Description"
	::= { qinqDomainEntry 6 }


-- 1.3.6.1.4.1.5875.800.3.7.8
qinqDomainServiceTable OBJECT-TYPE
	SYNTAX SEQUENCE OF QinqDomainServiceEntry
	MAX-ACCESS not-accessible
	STATUS current
	DESCRIPTION
		"Description"
	::= { qinq 8 }


-- 1.3.6.1.4.1.5875.800.3.7.8.1
qinqDomainServiceEntry OBJECT-TYPE
	SYNTAX QinqDomainServiceEntry
	MAX-ACCESS not-accessible
	STATUS current
	DESCRIPTION
		"Row Description"
	INDEX { qinqDomainName, qinqDomainServiceId }
	::= { qinqDomainServiceTable 1 }


QinqDomainServiceEntry ::=
	SEQUENCE { 
		qinqDomainServiceId
			Integer32,
		qinqDomainServiceType
			INTEGER,
		qinqDomainLayer1OldVlan
			Integer32,
		qinqDomainLayer1OldVlanCos
			Integer32,
		qinqDomainLayer1VlanAction
			Integer32,
		qinqDomainLayer1VlanCos
			Integer32,
		qinqDomainLayer1Tpid
			Integer32,
		qinqDomainLayer1NewVlan
			Integer32,
		qinqDomainLayer2OldVlan
			Integer32,
		qinqDomainLayer2OldVlanCos
			Integer32,
		qinqDomainLayer2VlanAction
			Integer32,
		qinqDomainLayer2VlanCos
			Integer32,
		qinqDomainLayer2Tpid
			Integer32,
		qinqDomainLayer2NewVlan
			Integer32,
		qinqDomainUpRuleType
			Integer32,
		qinqDomainUpRuleValue
			OCTET STRING,
		qinqDomainUpRuleOperation
			Integer32,
		qinqDomainDnRuleType
			Integer32,
		qinqDomainDnRuleValue
			OCTET STRING,
		qinqDomainDnRuleOperation
			Integer32,
		getNextQinqDomainServiceRuleID  
			Integer32,
		qinqDomainServiceAction
			RowStatus
	 }

-- 1.3.6.1.4.1.5875.800.3.7.8.1.1
qinqDomainServiceId OBJECT-TYPE
	SYNTAX Integer32
	MAX-ACCESS read-only
	STATUS current
	DESCRIPTION
		"Column Description"
	::= { qinqDomainServiceEntry 1 }


-- 1.3.6.1.4.1.5875.800.3.7.8.1.2
qinqDomainServiceType OBJECT-TYPE
	SYNTAX INTEGER
		{
		single(0),
		shared(1)
		}
	MAX-ACCESS read-write
	STATUS current
	DESCRIPTION
		"Column Description
		0:Single
		1:Shared"
	::= { qinqDomainServiceEntry 2 }


-- 1.3.6.1.4.1.5875.800.3.7.8.1.4
qinqDomainLayer1OldVlan OBJECT-TYPE
	SYNTAX Integer32 (0..4085 | 65535)
	MAX-ACCESS read-write
	STATUS current
	DESCRIPTION
		"Description:
		value:0~4085
		0xffff(65535)"
	::= { qinqDomainServiceEntry 4 }


-- 1.3.6.1.4.1.5875.800.3.7.8.1.5
qinqDomainLayer1OldVlanCos OBJECT-TYPE
	SYNTAX Integer32 (0..7)
	MAX-ACCESS read-write
	STATUS current
	DESCRIPTION
		"Description:
		value:0~7"
	::= { qinqDomainServiceEntry 5 }


-- 1.3.6.1.4.1.5875.800.3.7.8.1.6
qinqDomainLayer1VlanAction OBJECT-TYPE
	SYNTAX Integer32 (0..3)
	MAX-ACCESS read-write
	STATUS current
	DESCRIPTION
		"Description:
		1:add
		2:interpret
		3:transparent"
	::= { qinqDomainServiceEntry 6 }


-- 1.3.6.1.4.1.5875.800.3.7.8.1.7
qinqDomainLayer1VlanCos OBJECT-TYPE
	SYNTAX Integer32 (0..7 | 255)
	MAX-ACCESS read-write
	STATUS current
	DESCRIPTION
		"Description:
		1:value:0~7;
		2:255(null)"
	::= { qinqDomainServiceEntry 7 }


-- 1.3.6.1.4.1.5875.800.3.7.8.1.8
qinqDomainLayer1Tpid OBJECT-TYPE
	SYNTAX Integer32 (-2147483648..2147483647)
	MAX-ACCESS read-write
	STATUS current
	DESCRIPTION
		"Description"
	::= { qinqDomainServiceEntry 8 }


-- 1.3.6.1.4.1.5875.800.3.7.8.1.9
qinqDomainLayer1NewVlan OBJECT-TYPE
	SYNTAX Integer32 (1..4085 | 65535)
	MAX-ACCESS read-write
	STATUS current
	DESCRIPTION
		"Description:
		1:value 1~4085
		2: 0xffff(null)"
	::= { qinqDomainServiceEntry 9 }


-- 1.3.6.1.4.1.5875.800.3.7.8.1.10
qinqDomainLayer2OldVlan OBJECT-TYPE
	SYNTAX Integer32 (0..65535)
	MAX-ACCESS read-write
	STATUS current
	DESCRIPTION
		"Description:
		1:value 0~4085
		2:0xffff"
	::= { qinqDomainServiceEntry 10 }


-- 1.3.6.1.4.1.5875.800.3.7.8.1.11
qinqDomainLayer2OldVlanCos OBJECT-TYPE
	SYNTAX Integer32 (0..7)
	MAX-ACCESS read-write
	STATUS current
	DESCRIPTION
		"Description:
		value:0~7"
	::= { qinqDomainServiceEntry 11 }


-- 1.3.6.1.4.1.5875.800.3.7.8.1.12
qinqDomainLayer2VlanAction OBJECT-TYPE
	SYNTAX Integer32 (1..3)
	MAX-ACCESS read-write
	STATUS current
	DESCRIPTION
		"Description:
		1:add
		2:interpret
		3:transparent"
	::= { qinqDomainServiceEntry 12 }


-- 1.3.6.1.4.1.5875.800.3.7.8.1.13
qinqDomainLayer2VlanCos OBJECT-TYPE
	SYNTAX Integer32 (0..7 | 255)
	MAX-ACCESS read-write
	STATUS current
	DESCRIPTION
		"Description:
		1:value 0~7
		2:oxff(null)"
	::= { qinqDomainServiceEntry 13 }


-- 1.3.6.1.4.1.5875.800.3.7.8.1.14
qinqDomainLayer2Tpid OBJECT-TYPE
	SYNTAX Integer32
	MAX-ACCESS read-write
	STATUS current
	DESCRIPTION
		"Description"
	::= { qinqDomainServiceEntry 14 }


-- 1.3.6.1.4.1.5875.800.3.7.8.1.15
qinqDomainLayer2NewVlan OBJECT-TYPE
	SYNTAX Integer32 (1..4085 | 65535)
	MAX-ACCESS read-write
	STATUS current
	DESCRIPTION
		"Description:
		1:value0~4085	
		2:65535(null)"
	::= { qinqDomainServiceEntry 15 }


-- 1.3.6.1.4.1.5875.800.3.7.8.1.30
qinqDomainUpRuleType OBJECT-TYPE
	SYNTAX Integer32 (-2147483648..2147483647)
	MAX-ACCESS read-write
	STATUS current
	DESCRIPTION
		"Description"
	::= { qinqDomainServiceEntry 30 }


-- 1.3.6.1.4.1.5875.800.3.7.8.1.31
qinqDomainUpRuleValue OBJECT-TYPE
	SYNTAX OCTET STRING
	MAX-ACCESS read-write
	STATUS current
	DESCRIPTION
		"Description"
	::= { qinqDomainServiceEntry 31 }


-- 1.3.6.1.4.1.5875.800.3.7.8.1.32
qinqDomainUpRuleOperation OBJECT-TYPE
	SYNTAX Integer32 (-2147483648..2147483647)
	MAX-ACCESS read-write
	STATUS current
	DESCRIPTION
		"Description"
	::= { qinqDomainServiceEntry 32 }


-- 1.3.6.1.4.1.5875.800.3.7.8.1.33
qinqDomainDnRuleType OBJECT-TYPE
	SYNTAX Integer32 (-2147483648..2147483647)
	MAX-ACCESS read-write
	STATUS current
	DESCRIPTION
		"Description"
	::= { qinqDomainServiceEntry 33 }


-- 1.3.6.1.4.1.5875.800.3.7.8.1.34
qinqDomainDnRuleValue OBJECT-TYPE
	SYNTAX OCTET STRING
	MAX-ACCESS read-write
	STATUS current
	DESCRIPTION
		"Description"
	::= { qinqDomainServiceEntry 34 }


-- 1.3.6.1.4.1.5875.800.3.7.8.1.35
qinqDomainDnRuleOperation OBJECT-TYPE
	SYNTAX Integer32 (-2147483648..2147483647)
	MAX-ACCESS read-write
	STATUS current
	DESCRIPTION
		"Description"
	::= { qinqDomainServiceEntry 35 }

-- 1.3.6.1.4.1.5875.800.3.7.8.1.36
getNextQinqDomainServiceRuleID	OBJECT-TYPE	
	SYNTAX Integer32 (-2147483648..2147483647)
	MAX-ACCESS		read-only
	STATUS			current
	DESCRIPTION		"Description"
	::=  {  qinqDomainServiceEntry  36  }
			
-- 1.3.6.1.4.1.5875.800.3.7.8.1.100
qinqDomainServiceAction OBJECT-TYPE
	SYNTAX RowStatus
		{
		active(1),
		notInService(2),
		notReady(3),
		createAndGo(4),
		createAndWait(5),
		destroy(6),
		modify(7)
		}
	MAX-ACCESS read-create
	STATUS current
	DESCRIPTION
		"Description"
	::= { qinqDomainServiceEntry 100 }

qinqDomainServiceRuleTable	OBJECT-TYPE
	SYNTAX		SEQUENCE  OF  QinqDomainServiceRuleEntry
	MAX-ACCESS	not-accessible
	STATUS		current
	DESCRIPTION	"Description"
	::=  { qinq  9 }
	
qinqDomainServiceRuleEntry	OBJECT-TYPE
	SYNTAX		QinqDomainServiceRuleEntry
	MAX-ACCESS	not-accessible
	STATUS		current
	DESCRIPTION	"Row Description"
	INDEX		{  qinqDomainName, qinqDomainServiceId, qinqDomainServiceRuleIndex  }
	::=  { qinqDomainServiceRuleTable 1 }
	
QinqDomainServiceRuleEntry  ::=  SEQUENCE {
	qinqDomainServiceRuleIndex  Integer32,
	qinqDomainServiceUpRuleType  Integer32,
	qinqDomainServiceUpRuleValue  OCTET STRING,
	qinqDomainServiceUpRuleOperation  Integer32,
	qinqDomainServiceDnRuleType  Integer32,
	qinqDomainServiceDnRuleValue  OCTET STRING,
	qinqDomainServiceDnRuleOperation  Integer32,
	qinqDomainServiceRuleAction  RowStatus
	}
	
	
qinqDomainServiceRuleIndex	OBJECT-TYPE	
	SYNTAX			Integer32
	MAX-ACCESS		not-accessible
	STATUS			current
	DESCRIPTION		"Column Description"
	::=  {  qinqDomainServiceRuleEntry  3  }
	
	
qinqDomainServiceUpRuleType	OBJECT-TYPE	
	SYNTAX			Integer32
	MAX-ACCESS		read-write
	STATUS			current
	DESCRIPTION		"Column Description"
	::=  {  qinqDomainServiceRuleEntry  4  }
	
	
qinqDomainServiceUpRuleValue	OBJECT-TYPE	
	SYNTAX			OCTET STRING
	MAX-ACCESS		read-write
	STATUS			current
	DESCRIPTION		"Column Description"
	::=  {  qinqDomainServiceRuleEntry  5  }
	
	
qinqDomainServiceUpRuleOperation	OBJECT-TYPE	
	SYNTAX			Integer32
	MAX-ACCESS		read-write
	STATUS			current
	DESCRIPTION		"Column Description"
	::=  {  qinqDomainServiceRuleEntry  6  }
	
	
qinqDomainServiceDnRuleType	OBJECT-TYPE	
	SYNTAX			Integer32
	MAX-ACCESS		read-write
	STATUS			current
	DESCRIPTION		"Column Description"
	::=  {  qinqDomainServiceRuleEntry  7  }
	
	
qinqDomainServiceDnRuleValue	OBJECT-TYPE	
	SYNTAX			OCTET STRING
	MAX-ACCESS		read-write
	STATUS			current
	DESCRIPTION		"Column Description"
	::=  {  qinqDomainServiceRuleEntry  8  }
	
	
qinqDomainServiceDnRuleOperation	OBJECT-TYPE	
	SYNTAX			Integer32
	MAX-ACCESS		read-write
	STATUS			current
	DESCRIPTION		"Column Description"
	::=  {  qinqDomainServiceRuleEntry  9  }
	
	
qinqDomainServiceRuleAction	OBJECT-TYPE	
	SYNTAX			RowStatus  { active ( 1 ) , createAndGo ( 4 ) , destroy ( 6 ) , modify ( 7 ) } 
	MAX-ACCESS		read-create
	STATUS			current
	DESCRIPTION		"Column Description"
	::=  {  qinqDomainServiceRuleEntry  20  }	

-- 1.3.6.1.4.1.5875.800.3.8
ftthPerformance OBJECT IDENTIFIER ::= { oltData 8 }


-- 1.3.6.1.4.1.5875.800.3.8.1
ftthPerformanceCardEnableTable OBJECT-TYPE
	SYNTAX SEQUENCE OF FtthPerformanceCardEnableEntry
	MAX-ACCESS not-accessible
	STATUS current
	DESCRIPTION
		"Description"
	::= { ftthPerformance 1 }


-- 1.3.6.1.4.1.5875.800.3.8.1.1
ftthPerformanceCardEnableEntry OBJECT-TYPE
	SYNTAX FtthPerformanceCardEnableEntry
	MAX-ACCESS not-accessible
	STATUS current
	DESCRIPTION
		"Row Description"
	INDEX { slotIndex }
	::= { ftthPerformanceCardEnableTable 1 }


FtthPerformanceCardEnableEntry ::=
	SEQUENCE { 
		ftthPerformanceCardEnable
			Integer32
	 }

-- 1.3.6.1.4.1.5875.800.3.8.1.1.2
ftthPerformanceCardEnable OBJECT-TYPE
	SYNTAX Integer32
	MAX-ACCESS read-write
	STATUS current
	DESCRIPTION
		"  0-disable      1-enable"
	::= { ftthPerformanceCardEnableEntry 2 }


-- 1.3.6.1.4.1.5875.800.3.8.2
ftthIsPerformanceSupport OBJECT-TYPE
	SYNTAX INTEGER
		{
		unsupport(0),
		support(1)
		}
	MAX-ACCESS read-only
	STATUS current
	DESCRIPTION
		"Description :
		0:support
		1:unsupport"
	::= { ftthPerformance 2 }


-- 1.3.6.1.4.1.5875.800.3.8.3
ftthPerformanceEnableFor5516 OBJECT-TYPE
	SYNTAX INTEGER
		{
		disable(0),
		enable(1)
		}
	MAX-ACCESS read-write
	STATUS current
	DESCRIPTION
		"Description :
		0:disable
		1:enable"
	::= { ftthPerformance 3 }


-- 1.3.6.1.4.1.5875.800.3.8.6
ftthSystemPerformance OBJECT IDENTIFIER ::= { ftthPerformance 6 }


-- 1.3.6.1.4.1.5875.800.3.8.6.1
utilization OBJECT IDENTIFIER ::= { ftthSystemPerformance 1 }


-- 1.3.6.1.4.1.5875.800.3.8.6.1.1
cpuUtilization OBJECT-TYPE
	SYNTAX Integer32
	MAX-ACCESS read-only
	STATUS current
	DESCRIPTION
		"cpu utilization"
	::= { utilization 1 }


-- 1.3.6.1.4.1.5875.800.3.8.6.1.2
memUtilization OBJECT-TYPE
	SYNTAX Integer32
	MAX-ACCESS read-only
	STATUS current
	DESCRIPTION
		"mem utilization"
	::= { utilization 2 }


-- 1.3.6.1.4.1.5875.800.3.8.6.1.3
currentTemperature OBJECT-TYPE
	SYNTAX Integer32
	MAX-ACCESS read-only
	STATUS current
	DESCRIPTION
		"current Temperature"
	::= { utilization 3 }
 
ftthVlanTransmitPerformanceTable	OBJECT-TYPE
	SYNTAX		SEQUENCE  OF  FtthVlanTransmitPerformanceEntry
	MAX-ACCESS	not-accessible
	STATUS		current
	DESCRIPTION	"Description"
	::=  { ftthPerformance  7 }

ftthVlanTransmitPerformanceEntry	OBJECT-TYPE
	SYNTAX		FtthVlanTransmitPerformanceEntry
	MAX-ACCESS	not-accessible
	STATUS		current
	DESCRIPTION	"Row Description"
	INDEX		{  vlanID, uplinkIndex  }
	::=  { ftthVlanTransmitPerformanceTable 1 }

FtthVlanTransmitPerformanceEntry  ::=  SEQUENCE {
	vlanID  Integer32,
	framesUs  Counter32,
	framesDs  Counter32,
	octetsUs  Counter32,
	octetsDs  Counter32,
	discardsUs  Counter64,
	discardsDs  Counter64
	}


vlanID	OBJECT-TYPE	
	SYNTAX			Integer32  ( 1 .. 4096  ) 
	MAX-ACCESS		read-only
	STATUS			current
	DESCRIPTION		"Column Description"
	::=  {  ftthVlanTransmitPerformanceEntry  1  }


framesUs	OBJECT-TYPE	
	SYNTAX			Counter32
	MAX-ACCESS		read-only
	STATUS			current
	DESCRIPTION		"Up transmit messages"
	::=  {  ftthVlanTransmitPerformanceEntry  2  }


framesDs	OBJECT-TYPE	
	SYNTAX			Counter32
	MAX-ACCESS		read-only
	STATUS			current
	DESCRIPTION		"down transmit messages"
	::=  {  ftthVlanTransmitPerformanceEntry  3  }


octetsUs	OBJECT-TYPE	
	SYNTAX			Counter32
	MAX-ACCESS		read-only
	STATUS			current
	DESCRIPTION		"up transmit octets"
	::=  {  ftthVlanTransmitPerformanceEntry  4  }


octetsDs	OBJECT-TYPE	
	SYNTAX			Counter32
	MAX-ACCESS		read-only
	STATUS			current
	DESCRIPTION		"down transmit octets"
	::=  {  ftthVlanTransmitPerformanceEntry  5  }


discardsUs	OBJECT-TYPE	
	SYNTAX			Counter64
	MAX-ACCESS		read-only
	STATUS			current
	DESCRIPTION		"up discards messages"
	::=  {  ftthVlanTransmitPerformanceEntry  6  }


discardsDs	OBJECT-TYPE	
	SYNTAX			Counter64
	MAX-ACCESS		read-only
	STATUS			current
	DESCRIPTION		"down discards  messages"
	::=  {  ftthVlanTransmitPerformanceEntry  7  }


		
-- 1.3.6.1.4.1.5875.800.3.9
systemInfo OBJECT IDENTIFIER ::= { oltData 9 }


-- 1.3.6.1.4.1.5875.800.3.9.1
frameInfo OBJECT IDENTIFIER ::= { systemInfo 1 }


-- 1.3.6.1.4.1.5875.800.3.9.1.1
frameInfoTable OBJECT-TYPE
	SYNTAX SEQUENCE OF FrameInfoEntry
	MAX-ACCESS not-accessible
	STATUS current
	DESCRIPTION
		"Description"
	::= { frameInfo 1 }


-- 1.3.6.1.4.1.5875.800.3.9.1.1.1
frameInfoEntry OBJECT-TYPE
	SYNTAX FrameInfoEntry
	MAX-ACCESS not-accessible
	STATUS current
	DESCRIPTION
		"Row Description"
	INDEX { frameIndex }
	::= { frameInfoTable 1 }


FrameInfoEntry ::=
	SEQUENCE { 
		frameIndex
			Integer32,
		frameType
			Integer32,
		frameName
			OCTET STRING,
		slotNumOfFrame
			Integer32
	 }

-- 1.3.6.1.4.1.5875.800.3.9.1.1.1.1
frameIndex OBJECT-TYPE
	SYNTAX Integer32 (-2147483648..2147483647)
	MAX-ACCESS read-only
	STATUS current
	DESCRIPTION
		"Column Description"
	::= { frameInfoEntry 1 }


-- 1.3.6.1.4.1.5875.800.3.9.1.1.1.2
frameType OBJECT-TYPE
	SYNTAX Integer32 (-2147483648..2147483647)
	MAX-ACCESS read-only
	STATUS current
	DESCRIPTION
		"Column Description:
		1: An5116-02
		2: An5116-06
		11: An5516-01 1"
	::= { frameInfoEntry 2 }


-- 1.3.6.1.4.1.5875.800.3.9.1.1.1.3
frameName OBJECT-TYPE
	SYNTAX OCTET STRING
	MAX-ACCESS read-only
	STATUS current
	DESCRIPTION
		"Column Description"
	::= { frameInfoEntry 3 }


-- 1.3.6.1.4.1.5875.800.3.9.1.1.1.4
slotNumOfFrame OBJECT-TYPE
	SYNTAX Integer32 (-2147483648..2147483647)
	MAX-ACCESS read-only
	STATUS current
	DESCRIPTION
		"Column Description"
	::= { frameInfoEntry 4 }


-- 1.3.6.1.4.1.5875.800.3.9.2
cardInfo OBJECT IDENTIFIER ::= { systemInfo 2 }


-- 1.3.6.1.4.1.5875.800.3.9.2.1
cardInfoTable OBJECT-TYPE
	SYNTAX SEQUENCE OF CardInfoEntry
	MAX-ACCESS not-accessible
	STATUS current
	DESCRIPTION
		"Description"
	::= { cardInfo 1 }


-- 1.3.6.1.4.1.5875.800.3.9.2.1.1
cardInfoEntry OBJECT-TYPE
	SYNTAX CardInfoEntry
	MAX-ACCESS not-accessible
	STATUS current
	DESCRIPTION
		"Row Description"
	INDEX { slotIndex }
	::= { cardInfoTable 1 }


CardInfoEntry ::=
	SEQUENCE { 
		cardType
			Integer32,
		cardHardwareVersion
			OCTET STRING,
		cardSoftwateVersion
			OCTET STRING,
		cardStatus
			Integer32,
		cardNumOfPorts
			Integer32,
		cardAvailablePorts
			Integer32,
		cardCpuUtil
			Integer32,
		cardMemUtil
			Integer32
	 }

-- 1.3.6.1.4.1.5875.800.3.9.2.1.1.2
cardType OBJECT-TYPE
	SYNTAX Integer32 (-2147483648..2147483647)
	MAX-ACCESS read-only
	STATUS current
	DESCRIPTION
		"Column Description:
		260:EC2
		724:EC2-X
		16384:AC16
		the other type could see the card type table"
	::= { cardInfoEntry 2 }


-- 1.3.6.1.4.1.5875.800.3.9.2.1.1.3
cardHardwareVersion OBJECT-TYPE
	SYNTAX OCTET STRING
	MAX-ACCESS read-only
	STATUS current
	DESCRIPTION
		"Column Description"
	::= { cardInfoEntry 3 }


-- 1.3.6.1.4.1.5875.800.3.9.2.1.1.4
cardSoftwateVersion OBJECT-TYPE
	SYNTAX OCTET STRING
	MAX-ACCESS read-only
	STATUS current
	DESCRIPTION
		"Column Description"
	::= { cardInfoEntry 4 }


-- 1.3.6.1.4.1.5875.800.3.9.2.1.1.5
cardStatus OBJECT-TYPE
	SYNTAX Integer32 (-2147483648..2147483647)
	MAX-ACCESS read-only
	STATUS current
	DESCRIPTION
		"Column Description:
		1:normal(1)
		2:communication interrupt(0)"
	::= { cardInfoEntry 5 }


-- 1.3.6.1.4.1.5875.800.3.9.2.1.1.6
cardNumOfPorts OBJECT-TYPE
	SYNTAX Integer32 (-2147483648..2147483647)
	MAX-ACCESS read-only
	STATUS current
	DESCRIPTION
		"Column Description"
	::= { cardInfoEntry 6 }


-- 1.3.6.1.4.1.5875.800.3.9.2.1.1.7
cardAvailablePorts OBJECT-TYPE
	SYNTAX Integer32 (-2147483648..2147483647)
	MAX-ACCESS read-only
	STATUS current
	DESCRIPTION
		"Column Description"
	::= { cardInfoEntry 7 }


-- 1.3.6.1.4.1.5875.800.3.9.2.1.1.8
cardCpuUtil OBJECT-TYPE
	SYNTAX Integer32
	MAX-ACCESS read-only
	STATUS current
	DESCRIPTION
		"Description"
	::= { cardInfoEntry 8 }


-- 1.3.6.1.4.1.5875.800.3.9.2.1.1.9
cardMemUtil OBJECT-TYPE
	SYNTAX Integer32
	MAX-ACCESS read-only
	STATUS current
	DESCRIPTION
		"Description"
	::= { cardInfoEntry 9 }


-- 1.3.6.1.4.1.5875.800.3.9.3
interfaceInfo OBJECT IDENTIFIER ::= { systemInfo 3 }


-- 1.3.6.1.4.1.5875.800.3.9.3.1
portInfoTable OBJECT-TYPE
	SYNTAX SEQUENCE OF PortInfoEntry
	MAX-ACCESS not-accessible
	STATUS current
	DESCRIPTION
		"Description"
	::= { interfaceInfo 1 }


-- 1.3.6.1.4.1.5875.800.3.9.3.1.1
portInfoEntry OBJECT-TYPE
	SYNTAX PortInfoEntry
	MAX-ACCESS not-accessible
	STATUS current
	DESCRIPTION
		"Row Description"
	INDEX { portIndex }
	::= { portInfoTable 1 }


PortInfoEntry ::=
	SEQUENCE { 
		portType
			Integer32,
		portEnableStatus
			Integer32,
		portOnlineStatus
			Integer32,
		portSpeed
			Integer32,
		portName
			OCTET STRING,
		portDesc
			OCTET STRING,
		portMode
			Integer32,
		portVlan
			OCTET STRING,
		portMac
			OCTET STRING,
		portDefaultVlan
			Integer32,
		portAutoneg  
			Integer32

	 }

-- 1.3.6.1.4.1.5875.800.3.9.3.1.1.2
portType OBJECT-TYPE
	SYNTAX Integer32 (-2147483648..2147483647)
	MAX-ACCESS read-only
	STATUS current
	DESCRIPTION
		"Column Description"
	::= { portInfoEntry 2 }


-- 1.3.6.1.4.1.5875.800.3.9.3.1.1.3
portEnableStatus OBJECT-TYPE
	SYNTAX Integer32 (-2147483648..2147483647)
	MAX-ACCESS read-only
	STATUS current
	DESCRIPTION
		"0-disable
		1-enable"
	::= { portInfoEntry 3 }


-- 1.3.6.1.4.1.5875.800.3.9.3.1.1.4
portOnlineStatus OBJECT-TYPE
	SYNTAX Integer32 (-2147483648..2147483647)
	MAX-ACCESS read-only
	STATUS current
	DESCRIPTION
		"Description"
	::= { portInfoEntry 4 }


-- 1.3.6.1.4.1.5875.800.3.9.3.1.1.5
portSpeed OBJECT-TYPE
	SYNTAX Integer32 (-2147483648..2147483647)
	MAX-ACCESS read-only
	STATUS current
	DESCRIPTION
		"Description:
		0:10M
		1:100M
		2:1000M"
	::= { portInfoEntry 5 }


-- 1.3.6.1.4.1.5875.800.3.9.3.1.1.6
portName OBJECT-TYPE
	SYNTAX OCTET STRING
	MAX-ACCESS read-only
	STATUS current
	DESCRIPTION
		"Description"
	::= { portInfoEntry 6 }


-- 1.3.6.1.4.1.5875.800.3.9.3.1.1.7
portDesc OBJECT-TYPE
	SYNTAX OCTET STRING
	MAX-ACCESS read-write
	STATUS current
	DESCRIPTION
		"Description"
	::= { portInfoEntry 7 }


-- 1.3.6.1.4.1.5875.800.3.9.3.1.1.8
portMode OBJECT-TYPE
	SYNTAX Integer32
	MAX-ACCESS read-only
	STATUS current
	DESCRIPTION
		"Description:
		1:full duplex(1)
		2:half duplex(0)"
	::= { portInfoEntry 8 }


-- 1.3.6.1.4.1.5875.800.3.9.3.1.1.9
portVlan OBJECT-TYPE
	SYNTAX OCTET STRING
	MAX-ACCESS read-only
	STATUS current
	DESCRIPTION
		"Description"
	::= { portInfoEntry 9 }


-- 1.3.6.1.4.1.5875.800.3.9.3.1.1.10
portMac OBJECT-TYPE
	SYNTAX OCTET STRING
	MAX-ACCESS read-only
	STATUS current
	DESCRIPTION
		"Description"
	::= { portInfoEntry 10 }


-- 1.3.6.1.4.1.5875.800.3.9.3.1.1.11
portDefaultVlan OBJECT-TYPE
	SYNTAX Integer32
	MAX-ACCESS read-only
	STATUS current
	DESCRIPTION
		"Description"
	::= { portInfoEntry 11 }

portAutoneg	OBJECT-TYPE	
	SYNTAX			Integer32  ( 0 .. 1  ) 
	MAX-ACCESS		read-only
	STATUS			current
	DESCRIPTION		"Description"
	::=  {  portInfoEntry  12  }
		
-- 1.3.6.1.4.1.5875.800.3.9.3.2
potsInfoTable OBJECT-TYPE
	SYNTAX SEQUENCE OF PotsInfoEntry
	MAX-ACCESS not-accessible
	STATUS current
	DESCRIPTION
		"Description"
	::= { interfaceInfo 2 }


-- 1.3.6.1.4.1.5875.800.3.9.3.2.1
potsInfoEntry OBJECT-TYPE
	SYNTAX PotsInfoEntry
	MAX-ACCESS not-accessible
	STATUS current
	DESCRIPTION
		"Row Description"
	INDEX { potsIndex }
	::= { potsInfoTable 1 }


PotsInfoEntry ::=
	SEQUENCE { 
		potsType
			Integer32,
		potsName
			OCTET STRING,
		potsDesc
			OCTET STRING,
		potsEnableStatus
			Integer32,
		potsIdleStatus
			Integer32
	 }

-- 1.3.6.1.4.1.5875.800.3.9.3.2.1.1
potsType OBJECT-TYPE
	SYNTAX Integer32 (-2147483648..2147483647)
	MAX-ACCESS read-only
	STATUS current
	DESCRIPTION
		"Column Description"
	::= { potsInfoEntry 1 }


-- 1.3.6.1.4.1.5875.800.3.9.3.2.1.2
potsName OBJECT-TYPE
	SYNTAX OCTET STRING
	MAX-ACCESS read-only
	STATUS current
	DESCRIPTION
		"Column Description"
	::= { potsInfoEntry 2 }


-- 1.3.6.1.4.1.5875.800.3.9.3.2.1.3
potsDesc OBJECT-TYPE
	SYNTAX OCTET STRING
	MAX-ACCESS read-write
	STATUS current
	DESCRIPTION
		"Column Description"
	::= { potsInfoEntry 3 }


-- 1.3.6.1.4.1.5875.800.3.9.3.2.1.4
potsEnableStatus OBJECT-TYPE
	SYNTAX Integer32
	MAX-ACCESS read-only
	STATUS current
	DESCRIPTION
		"Column Description:
		1:enable(1)
		2:disable(2)"
	::= { potsInfoEntry 4 }


-- 1.3.6.1.4.1.5875.800.3.9.3.2.1.5
potsIdleStatus OBJECT-TYPE
	SYNTAX Integer32
	MAX-ACCESS read-only
	STATUS current
	DESCRIPTION
		"Column Description"
	::= { potsInfoEntry 5 }


-- 1.3.6.1.4.1.5875.800.3.9.3.3
onuPonInfoTable OBJECT-TYPE
	SYNTAX SEQUENCE OF OnuPonInfoEntry
	MAX-ACCESS not-accessible
	STATUS current
	DESCRIPTION
		"Description"
	::= { interfaceInfo 3 }


-- 1.3.6.1.4.1.5875.800.3.9.3.3.1
onuPonInfoEntry OBJECT-TYPE
	SYNTAX OnuPonInfoEntry
	MAX-ACCESS not-accessible
	STATUS current
	DESCRIPTION
		"Row Description"
	INDEX { onuIndex }
	::= { onuPonInfoTable 1 }


OnuPonInfoEntry ::=
	SEQUENCE { 
		onuPonType
			Integer32,
		onuPonName
			OCTET STRING,
		onuPonDesc
			OCTET STRING,
		onuPonEnableStatus
			Integer32,
		onuPonSpeed
			Integer32,
		onuPonRxOpticalPower
			Integer32,
		onuPonTxOpticalPower
			Integer32,
		onuPonOpticalVltage
			Integer32,
		onuPonOpticalCurrent
			Integer32,
		onuPonOpticalTemperature
			Integer32,
		onuPonIsOpticalPowerValid
			INTEGER,
		onuPonUpstreamSpeed
			Integer32					
			
	 }

-- 1.3.6.1.4.1.5875.800.3.9.3.3.1.1
onuPonType OBJECT-TYPE
	SYNTAX Integer32
	MAX-ACCESS read-only
	STATUS current
	DESCRIPTION
		"Column Description"
	::= { onuPonInfoEntry 1 }


-- 1.3.6.1.4.1.5875.800.3.9.3.3.1.2
onuPonName OBJECT-TYPE
	SYNTAX OCTET STRING
	MAX-ACCESS read-only
	STATUS current
	DESCRIPTION
		"Column Description"
	::= { onuPonInfoEntry 2 }


-- 1.3.6.1.4.1.5875.800.3.9.3.3.1.3
onuPonDesc OBJECT-TYPE
	SYNTAX OCTET STRING
	MAX-ACCESS read-write
	STATUS current
	DESCRIPTION
		"Column Description"
	::= { onuPonInfoEntry 3 }


-- 1.3.6.1.4.1.5875.800.3.9.3.3.1.4
onuPonEnableStatus OBJECT-TYPE
	SYNTAX Integer32
	MAX-ACCESS read-only
	STATUS current
	DESCRIPTION
		"Column Description"
	::= { onuPonInfoEntry 4 }


-- 1.3.6.1.4.1.5875.800.3.9.3.3.1.5
onuPonSpeed OBJECT-TYPE
	SYNTAX Integer32
	MAX-ACCESS read-only
	STATUS current
	DESCRIPTION
		"Column Description"
	::= { onuPonInfoEntry 5 }


-- 1.3.6.1.4.1.5875.800.3.9.3.3.1.6
onuPonRxOpticalPower OBJECT-TYPE
	SYNTAX Integer32
	MAX-ACCESS read-only
	STATUS current
	DESCRIPTION
		"Column Description"
	::= { onuPonInfoEntry 6 }


-- 1.3.6.1.4.1.5875.800.3.9.3.3.1.7
onuPonTxOpticalPower OBJECT-TYPE
	SYNTAX Integer32
	MAX-ACCESS read-only
	STATUS current
	DESCRIPTION
		"Column Description"
	::= { onuPonInfoEntry 7 }


-- 1.3.6.1.4.1.5875.800.3.9.3.3.1.8
onuPonOpticalVltage OBJECT-TYPE
	SYNTAX Integer32
	MAX-ACCESS read-only
	STATUS current
	DESCRIPTION
		"Column Description"
	::= { onuPonInfoEntry 8 }


-- 1.3.6.1.4.1.5875.800.3.9.3.3.1.9
onuPonOpticalCurrent OBJECT-TYPE
	SYNTAX Integer32
	MAX-ACCESS read-only
	STATUS current
	DESCRIPTION
		"Column Description"
	::= { onuPonInfoEntry 9 }


-- 1.3.6.1.4.1.5875.800.3.9.3.3.1.10
onuPonOpticalTemperature OBJECT-TYPE
	SYNTAX Integer32
	MAX-ACCESS read-only
	STATUS current
	DESCRIPTION
		"Column Description"
	::= { onuPonInfoEntry 10 }


-- 1.3.6.1.4.1.5875.800.3.9.3.3.1.11
onuPonIsOpticalPowerValid OBJECT-TYPE
	SYNTAX INTEGER
		{
		support(1),
		nonsupport(2)
		}
	MAX-ACCESS read-write
	STATUS current
	DESCRIPTION
		"Description:
		1:support
		2:nonsupport"
	::= { onuPonInfoEntry 11 }

onuPonUpstreamSpeed	OBJECT-TYPE	
	SYNTAX			Integer32
	MAX-ACCESS		read-only
	STATUS			current
	DESCRIPTION		"Description"
	::=  {  onuPonInfoEntry  12  }


-- 1.3.6.1.4.1.5875.800.3.9.3.4
oltPonInfoTable OBJECT-TYPE
	SYNTAX SEQUENCE OF OltPonInfoEntry
	MAX-ACCESS not-accessible
	STATUS current
	DESCRIPTION
		"Description"
	::= { interfaceInfo 4 }


-- 1.3.6.1.4.1.5875.800.3.9.3.4.1
oltPonInfoEntry OBJECT-TYPE
	SYNTAX OltPonInfoEntry
	MAX-ACCESS not-accessible
	STATUS current
	DESCRIPTION
		"Row Description"
	INDEX { ponIndex }
	::= { oltPonInfoTable 1 }


OltPonInfoEntry ::=
	SEQUENCE { 
		oltPonType
			Integer32,
		oltPonName
			OCTET STRING,
		oltPonDesc
			OCTET STRING,
		oltPonEnableStatus
			Integer32,
		oltPonOnlineStatus
			Integer32,
		oltPonSpeed
			Integer32,
		oltPonTxOpticalPower
			Integer32,
		oltPonOpticalVltage
			Integer32,
		oltPonOpticalCurrent
			Integer32,
		oltPonOpticalTemperature
			Integer32,
		oltPonAuthOnuNum
			Integer32,
		oltPonUpStreamSpeed
		  Integer32					
	 }

-- 1.3.6.1.4.1.5875.800.3.9.3.4.1.1
oltPonType OBJECT-TYPE
	SYNTAX Integer32
	MAX-ACCESS read-only
	STATUS current
	DESCRIPTION
		"Column Description"
	::= { oltPonInfoEntry 1 }


-- 1.3.6.1.4.1.5875.800.3.9.3.4.1.2
oltPonName OBJECT-TYPE
	SYNTAX OCTET STRING
	MAX-ACCESS read-only
	STATUS current
	DESCRIPTION
		"Column Description"
	::= { oltPonInfoEntry 2 }


-- 1.3.6.1.4.1.5875.800.3.9.3.4.1.3
oltPonDesc OBJECT-TYPE
	SYNTAX OCTET STRING
	MAX-ACCESS read-write
	STATUS current
	DESCRIPTION
		"Column Description"
	::= { oltPonInfoEntry 3 }


-- 1.3.6.1.4.1.5875.800.3.9.3.4.1.4
oltPonEnableStatus OBJECT-TYPE
	SYNTAX Integer32
	MAX-ACCESS read-only
	STATUS current
	DESCRIPTION
		"Column Description"
	::= { oltPonInfoEntry 4 }


-- 1.3.6.1.4.1.5875.800.3.9.3.4.1.5
oltPonOnlineStatus OBJECT-TYPE
	SYNTAX Integer32
	MAX-ACCESS read-only
	STATUS current
	DESCRIPTION
		"Column Description:
		1:occupied(1)
		2:empty(0)"
	::= { oltPonInfoEntry 5 }


-- 1.3.6.1.4.1.5875.800.3.9.3.4.1.6
oltPonSpeed OBJECT-TYPE
	SYNTAX Integer32
	MAX-ACCESS read-only
	STATUS current
	DESCRIPTION
		"Column Description:
		unit bps
		0:10M
		1:100M
		2:1000M"
	::= { oltPonInfoEntry 6 }

-- 1.3.6.1.4.1.5875.800.3.9.3.4.1.8
oltPonTxOpticalPower OBJECT-TYPE
	SYNTAX Integer32
	MAX-ACCESS read-only
	STATUS current
	DESCRIPTION
		"Column Description"
	::= { oltPonInfoEntry 8 }


-- 1.3.6.1.4.1.5875.800.3.9.3.4.1.9
oltPonOpticalVltage OBJECT-TYPE
	SYNTAX Integer32
	MAX-ACCESS read-only
	STATUS current
	DESCRIPTION
		"Column Description"
	::= { oltPonInfoEntry 9 }


-- 1.3.6.1.4.1.5875.800.3.9.3.4.1.10
oltPonOpticalCurrent OBJECT-TYPE
	SYNTAX Integer32
	MAX-ACCESS read-only
	STATUS current
	DESCRIPTION
		"Column Description"
	::= { oltPonInfoEntry 10 }


-- 1.3.6.1.4.1.5875.800.3.9.3.4.1.11
oltPonOpticalTemperature OBJECT-TYPE
	SYNTAX Integer32
	MAX-ACCESS read-only
	STATUS current
	DESCRIPTION
		"Column Description"
	::= { oltPonInfoEntry 11 }


-- 1.3.6.1.4.1.5875.800.3.9.3.4.1.12
oltPonAuthOnuNum OBJECT-TYPE
	SYNTAX Integer32 (-2147483648..2147483647)
	MAX-ACCESS read-only
	STATUS current
	DESCRIPTION
		"Description"
	::= { oltPonInfoEntry 12 }

oltPonUpStreamSpeed	OBJECT-TYPE	
	SYNTAX			Integer32
	MAX-ACCESS		read-only
	STATUS			current
	DESCRIPTION		"Description"
	::=  {  oltPonInfoEntry  13  }


-- 1.3.6.1.4.1.5875.800.3.9.3.5
oltUplinkInfoTable OBJECT-TYPE
	SYNTAX SEQUENCE OF OltUplinkInfoEntry
	MAX-ACCESS not-accessible
	STATUS current
	DESCRIPTION
		"Description"
	::= { interfaceInfo 5 }


-- 1.3.6.1.4.1.5875.800.3.9.3.5.1
oltUplinkInfoEntry OBJECT-TYPE
	SYNTAX OltUplinkInfoEntry
	MAX-ACCESS not-accessible
	STATUS current
	DESCRIPTION
		"Row Description"
	INDEX { uplinkIndex }
	::= { oltUplinkInfoTable 1 }


OltUplinkInfoEntry ::=
	SEQUENCE { 
		uplinkType
			Integer32,
		uplinkName
			OCTET STRING,
		uplinkDesc
			OCTET STRING,
		uplinkEnableStatus
			Integer32,
		uplinkSpeed
			Integer32
	 }

-- 1.3.6.1.4.1.5875.800.3.9.3.5.1.1
uplinkType OBJECT-TYPE
	SYNTAX Integer32 (-2147483648..2147483647)
	MAX-ACCESS read-only
	STATUS current
	DESCRIPTION
		"Column Description:
		AN5516_01B:
		0:FE
		1:GE
		2:XGE /*10G*/
		4:TRUNK"
	::= { oltUplinkInfoEntry 1 }


-- 1.3.6.1.4.1.5875.800.3.9.3.5.1.2
uplinkName OBJECT-TYPE
	SYNTAX OCTET STRING
	MAX-ACCESS read-only
	STATUS current
	DESCRIPTION
		"Column Description"
	::= { oltUplinkInfoEntry 2 }


-- 1.3.6.1.4.1.5875.800.3.9.3.5.1.3
uplinkDesc OBJECT-TYPE
	SYNTAX OCTET STRING
	MAX-ACCESS read-write
	STATUS current
	DESCRIPTION
		"Column Description"
	::= { oltUplinkInfoEntry 3 }


-- 1.3.6.1.4.1.5875.800.3.9.3.5.1.4
uplinkEnableStatus OBJECT-TYPE
	SYNTAX Integer32
	MAX-ACCESS read-only
	STATUS current
	DESCRIPTION
		"Column Description:
		1:enable(1)
		2:disable(2)"
	::= { oltUplinkInfoEntry 4 }


-- 1.3.6.1.4.1.5875.800.3.9.3.5.1.5
uplinkSpeed OBJECT-TYPE
	SYNTAX Integer32
	MAX-ACCESS read-only
	STATUS current
	DESCRIPTION
		"Column Description:
		unit:bps"
	::= { oltUplinkInfoEntry 5 }


-- 1.3.6.1.4.1.5875.800.3.9.3.6
oltPonOpticalStatisticsTable OBJECT-TYPE
	SYNTAX SEQUENCE OF OltPonOpticalStatisticsEntry
	MAX-ACCESS not-accessible
	STATUS current
	DESCRIPTION
		"Description"
	::= { interfaceInfo 6 }


-- 1.3.6.1.4.1.5875.800.3.9.3.6.1
oltPonopticalStatisticsEntry OBJECT-TYPE
	SYNTAX OltPonOpticalStatisticsEntry
	MAX-ACCESS not-accessible
	STATUS current
	DESCRIPTION
		"Row Description"
	INDEX { ponIndex }
	::= { oltPonOpticalStatisticsTable 1 }


OltPonOpticalStatisticsEntry ::=
	SEQUENCE { 
		oltPonOpticalStatisticsSwitch
			Integer32
	 }

-- 1.3.6.1.4.1.5875.800.3.9.3.6.1.1
oltPonOpticalStatisticsSwitch OBJECT-TYPE
	SYNTAX Integer32
	MAX-ACCESS read-write
	STATUS current
	DESCRIPTION
		"Column Description"
	::= { oltPonopticalStatisticsEntry 1 }


oltPonRxOpticalPowerTable	OBJECT-TYPE
	SYNTAX		SEQUENCE  OF  OltPonRxOpticalPowerEntry
	MAX-ACCESS	not-accessible
	STATUS		current
	DESCRIPTION	"Description"
	::=  { interfaceInfo  7 }

oltPonRxOpticalPowerEntry	OBJECT-TYPE
	SYNTAX		OltPonRxOpticalPowerEntry
	MAX-ACCESS	not-accessible
	STATUS		current
	DESCRIPTION	"Row Description"
	INDEX		{  ponIndex, onuNoRxOpticalPower  }
	::=  { oltPonRxOpticalPowerTable 1 }

OltPonRxOpticalPowerEntry  ::=  SEQUENCE {
	onuNoRxOpticalPower  Integer32,
	oltPonRxOpticalPower  Integer32
	}


onuNoRxOpticalPower	OBJECT-TYPE	
	SYNTAX			Integer32
	MAX-ACCESS		not-accessible
	STATUS			current
	DESCRIPTION		"Column Description"
	::=  {  oltPonRxOpticalPowerEntry  1  }


oltPonRxOpticalPower	OBJECT-TYPE	
	SYNTAX			Integer32
	MAX-ACCESS		read-only
	STATUS			current
	DESCRIPTION		"Description"
	::=  {  oltPonRxOpticalPowerEntry  2  }


-- 1.3.6.1.4.1.5875.800.3.9.4
sysInfo OBJECT IDENTIFIER ::= { systemInfo 4 }


-- 1.3.6.1.4.1.5875.800.3.9.4.1
sysIp OBJECT-TYPE
	SYNTAX IpAddress
	MAX-ACCESS read-only
	STATUS current
	DESCRIPTION
		"Description"
	::= { sysInfo 1 }


-- 1.3.6.1.4.1.5875.800.3.9.4.2
sysMac OBJECT-TYPE
	SYNTAX MacAddress
	MAX-ACCESS read-only
	STATUS current
	DESCRIPTION
		"Description"
	::= { sysInfo 2 }


-- 1.3.6.1.4.1.5875.800.3.9.4.3
sysSoftVersion OBJECT-TYPE
	SYNTAX OCTET STRING
	MAX-ACCESS read-only
	STATUS current
	DESCRIPTION
		"Description"
	::= { sysInfo 3 }


-- 1.3.6.1.4.1.5875.800.3.9.4.4
sysHardVersion OBJECT-TYPE
	SYNTAX OCTET STRING
	MAX-ACCESS read-only
	STATUS current
	DESCRIPTION
		"Description"
	::= { sysInfo 4 }


-- 1.3.6.1.4.1.5875.800.3.9.4.5
sysTemperature OBJECT-TYPE
	SYNTAX Integer32
	MAX-ACCESS read-only
	STATUS current
	DESCRIPTION
		"Description"
	::= { sysInfo 5 }


-- 1.3.6.1.4.1.5875.800.3.9.5
slotInfoFor5516 OBJECT IDENTIFIER ::= { systemInfo 5 }


-- 1.3.6.1.4.1.5875.800.3.9.5.1
slotInfoTable OBJECT-TYPE
	SYNTAX SEQUENCE OF SlotInfoEntry
	MAX-ACCESS not-accessible
	STATUS current
	DESCRIPTION
		"Description"
	::= { slotInfoFor5516 1 }


-- 1.3.6.1.4.1.5875.800.3.9.5.1.1
slotInfoEntry OBJECT-TYPE
	SYNTAX SlotInfoEntry
	MAX-ACCESS not-accessible
	STATUS current
	DESCRIPTION
		"Row Description"
	INDEX { slotIndex }
	::= { slotInfoTable 1 }


SlotInfoEntry ::=
	SEQUENCE { 
		occupiedStatus
			INTEGER,
		authCardType
			Integer32,
		occupiedCardType
			Integer32
	 }

-- 1.3.6.1.4.1.5875.800.3.9.5.1.1.2
occupiedStatus OBJECT-TYPE
	SYNTAX INTEGER
		{
		occupied(1),
		empty(0)
		}
	MAX-ACCESS read-only
	STATUS current
	DESCRIPTION
		"Column Description:
		1:occupied(1)
		2:empty(0)"
	::= { slotInfoEntry 2 }


-- 1.3.6.1.4.1.5875.800.3.9.5.1.1.3
authCardType OBJECT-TYPE
	SYNTAX Integer32
	MAX-ACCESS read-only
	STATUS current
	DESCRIPTION
		"Column Description"
	::= { slotInfoEntry 3 }


-- 1.3.6.1.4.1.5875.800.3.9.5.1.1.4
occupiedCardType OBJECT-TYPE
	SYNTAX Integer32
	MAX-ACCESS read-only
	STATUS current
	DESCRIPTION
		"Column Description"
	::= { slotInfoEntry 4 }


-- 1.3.6.1.4.1.5875.800.3.9.6
onu2PonLength OBJECT IDENTIFIER ::= { systemInfo 6 }


-- 1.3.6.1.4.1.5875.800.3.9.6.1
onu2PonLengthTable OBJECT-TYPE
	SYNTAX SEQUENCE OF Onu2PonLengthEntry
	MAX-ACCESS not-accessible
	STATUS current
	DESCRIPTION
		"Description"
	::= { onu2PonLength 1 }


-- 1.3.6.1.4.1.5875.800.3.9.6.1.1
onu2PonLengthEntry OBJECT-TYPE
	SYNTAX Onu2PonLengthEntry
	MAX-ACCESS not-accessible
	STATUS current
	DESCRIPTION
		"Row Description"
	INDEX { onuIndex }
	::= { onu2PonLengthTable 1 }


Onu2PonLengthEntry ::=
	SEQUENCE { 
		length
			Integer32
	 }

-- 1.3.6.1.4.1.5875.800.3.9.6.1.1.1
length OBJECT-TYPE
	SYNTAX Integer32
	MAX-ACCESS read-only
	STATUS current
	DESCRIPTION
		"Column Description:
		need the onu online, otherwise the length will be zero"
	::= { onu2PonLengthEntry 1 }


-- 1.3.6.1.4.1.5875.800.3.9.8
mgrCardInfo OBJECT IDENTIFIER ::= { systemInfo 8 }


-- 1.3.6.1.4.1.5875.800.3.9.8.1
mgrCardInfoTable OBJECT-TYPE
	SYNTAX SEQUENCE OF MgrCardInfoEntry
	MAX-ACCESS not-accessible
	STATUS current
	DESCRIPTION
		"Description"
	::= { mgrCardInfo 1 }


-- 1.3.6.1.4.1.5875.800.3.9.8.1.1
mgrCardInfoEntry OBJECT-TYPE
	SYNTAX MgrCardInfoEntry
	MAX-ACCESS not-accessible
	STATUS current
	DESCRIPTION
		"Row Description"
	INDEX { slotIndex }
	::= { mgrCardInfoTable 1 }


MgrCardInfoEntry ::=
	SEQUENCE { 
		mgrCardType
			Integer32,
		mgrCardHandwareVersion
			OCTET STRING,
		mgrCardSoftwareVession
			OCTET STRING,
		mgrCardWorkStatus
			Integer32,
		mgrCardCpuUtil
			Integer32,
		mgrCardMemUtil
			Integer32
	 }

-- 1.3.6.1.4.1.5875.800.3.9.8.1.1.1
mgrCardType OBJECT-TYPE
	SYNTAX Integer32
	MAX-ACCESS read-only
	STATUS current
	DESCRIPTION
		"Column Description
		1:normal(1)
		2:communication interrupt(0)"
	::= { mgrCardInfoEntry 1 }


-- 1.3.6.1.4.1.5875.800.3.9.8.1.1.2
mgrCardHandwareVersion OBJECT-TYPE
	SYNTAX OCTET STRING
	MAX-ACCESS read-only
	STATUS current
	DESCRIPTION
		"Column Description"
	::= { mgrCardInfoEntry 2 }


-- 1.3.6.1.4.1.5875.800.3.9.8.1.1.3
mgrCardSoftwareVession OBJECT-TYPE
	SYNTAX OCTET STRING
	MAX-ACCESS read-only
	STATUS current
	DESCRIPTION
		"Column Description"
	::= { mgrCardInfoEntry 3 }


-- 1.3.6.1.4.1.5875.800.3.9.8.1.1.4
mgrCardWorkStatus OBJECT-TYPE
	SYNTAX Integer32
	MAX-ACCESS read-only
	STATUS current
	DESCRIPTION
		"Column Description"
	::= { mgrCardInfoEntry 4 }


-- 1.3.6.1.4.1.5875.800.3.9.8.1.1.5
mgrCardCpuUtil OBJECT-TYPE
	SYNTAX Integer32
	MAX-ACCESS read-only
	STATUS current
	DESCRIPTION
		"Column Description"
	::= { mgrCardInfoEntry 5 }


-- 1.3.6.1.4.1.5875.800.3.9.8.1.1.6
mgrCardMemUtil OBJECT-TYPE
	SYNTAX Integer32
	MAX-ACCESS read-only
	STATUS current
	DESCRIPTION
		"Column Description"
	::= { mgrCardInfoEntry 6 }


-- 1.3.6.1.4.1.5875.800.3.10
authOnuInf OBJECT IDENTIFIER ::= { oltData 10 }


-- 1.3.6.1.4.1.5875.800.3.10.1
authOnuListTable OBJECT-TYPE
	SYNTAX SEQUENCE OF AuthOnuListEntry
	MAX-ACCESS not-accessible
	STATUS current
	DESCRIPTION
		"Description"
	::= { authOnuInf 1 }


-- 1.3.6.1.4.1.5875.800.3.10.1.1
authOnuListEntry OBJECT-TYPE
	SYNTAX AuthOnuListEntry
	MAX-ACCESS not-accessible
	STATUS current
	DESCRIPTION
		"Row Description"
	INDEX { onuIndex }
	::= { authOnuListTable 1 }


AuthOnuListEntry ::=
	SEQUENCE { 
		authOnuListSlot
			Integer32,
		authOnuListPon
			Integer32,
		authOnuListOnuid
			Integer32,
		authOnuListOnuType
			Integer32,
		authOnuListIp
			OCTET STRING,
		authOnuListName
			OCTET STRING,
		authOnuListSnLoid
			OCTET STRING,
		authOnuListSnPwd
			OCTET STRING,
		authOnuListMac
			OCTET STRING,
		onuStatus
			Integer32,
		authOnuSoftwareVersion
			OCTET STRING,
		authOnuHardwareVersion
			OCTET STRING,
		authOnuFirmwareVersion
			OCTET STRING
	 }

-- 1.3.6.1.4.1.5875.800.3.10.1.1.2
authOnuListSlot OBJECT-TYPE
	SYNTAX Integer32
	MAX-ACCESS read-only
	STATUS current
	DESCRIPTION
		"Column Description"
	::= { authOnuListEntry 2 }


-- 1.3.6.1.4.1.5875.800.3.10.1.1.3
authOnuListPon OBJECT-TYPE
	SYNTAX Integer32
	MAX-ACCESS read-only
	STATUS current
	DESCRIPTION
		"Column Description"
	::= { authOnuListEntry 3 }


-- 1.3.6.1.4.1.5875.800.3.10.1.1.4
authOnuListOnuid OBJECT-TYPE
	SYNTAX Integer32
	MAX-ACCESS read-only
	STATUS current
	DESCRIPTION
		"Column Description"
	::= { authOnuListEntry 4 }


-- 1.3.6.1.4.1.5875.800.3.10.1.1.5
authOnuListOnuType OBJECT-TYPE
	SYNTAX Integer32
	MAX-ACCESS read-only
	STATUS current
	DESCRIPTION
		"Column Description"
	::= { authOnuListEntry 5 }


-- 1.3.6.1.4.1.5875.800.3.10.1.1.6
authOnuListIp OBJECT-TYPE
	SYNTAX OCTET STRING
	MAX-ACCESS read-only
	STATUS current
	DESCRIPTION
		"Column Description"
	::= { authOnuListEntry 6 }


-- 1.3.6.1.4.1.5875.800.3.10.1.1.7
authOnuListName OBJECT-TYPE
	SYNTAX OCTET STRING
	MAX-ACCESS read-only
	STATUS current
	DESCRIPTION
		"Column Description"
	::= { authOnuListEntry 7 }


-- 1.3.6.1.4.1.5875.800.3.10.1.1.8
authOnuListSnLoid OBJECT-TYPE
	SYNTAX OCTET STRING
	MAX-ACCESS read-only
	STATUS current
	DESCRIPTION
		"Column Description"
	::= { authOnuListEntry 8 }


-- 1.3.6.1.4.1.5875.800.3.10.1.1.9
authOnuListSnPwd OBJECT-TYPE
	SYNTAX OCTET STRING
	MAX-ACCESS read-only
	STATUS current
	DESCRIPTION
		"Column Description"
	::= { authOnuListEntry 9 }


-- 1.3.6.1.4.1.5875.800.3.10.1.1.10
authOnuListMac OBJECT-TYPE
	SYNTAX OCTET STRING
	MAX-ACCESS read-only
	STATUS current
	DESCRIPTION
		"Column Description"
	::= { authOnuListEntry 10 }


-- 1.3.6.1.4.1.5875.800.3.10.1.1.11
onuStatus OBJECT-TYPE
	SYNTAX Integer32 (0..1)
	MAX-ACCESS read-only
	STATUS current
	DESCRIPTION
		"Description:
		1:offonline/fiber cut/power failure(0)
		2:online(1)"
	::= { authOnuListEntry 11 }


-- 1.3.6.1.4.1.5875.800.3.10.1.1.12
authOnuSoftwareVersion OBJECT-TYPE
	SYNTAX OCTET STRING
	MAX-ACCESS read-only
	STATUS current
	DESCRIPTION
		"Description"
	::= { authOnuListEntry 12 }


-- 1.3.6.1.4.1.5875.800.3.10.1.1.13
authOnuHardwareVersion OBJECT-TYPE
	SYNTAX OCTET STRING
	MAX-ACCESS read-only
	STATUS current
	DESCRIPTION
		"Description"
	::= { authOnuListEntry 13 }


-- 1.3.6.1.4.1.5875.800.3.10.1.1.14
authOnuFirmwareVersion OBJECT-TYPE
	SYNTAX OCTET STRING
	MAX-ACCESS read-only
	STATUS current
	DESCRIPTION
		"Description"
	::= { authOnuListEntry 14 }


-- 1.3.6.1.4.1.5875.800.3.11
unauthOnuList OBJECT IDENTIFIER ::= { oltData 11 }


-- 1.3.6.1.4.1.5875.800.3.11.1
unauthOnuListTable OBJECT-TYPE
	SYNTAX SEQUENCE OF UnauthOnuListEntry
	MAX-ACCESS not-accessible
	STATUS current
	DESCRIPTION
		"Description"
	::= { unauthOnuList 1 }


-- 1.3.6.1.4.1.5875.800.3.11.1.1
unauthOnuListEntry OBJECT-TYPE
	SYNTAX UnauthOnuListEntry
	MAX-ACCESS not-accessible
	STATUS current
	DESCRIPTION
		"Row Description"
	INDEX { unauthOnuListOnuIndex }
	::= { unauthOnuListTable 1 }


UnauthOnuListEntry ::=
	SEQUENCE { 
		unauthOnuListOnuIndex
			Integer32,
		unauthOnuListSlot
			Integer32,
		unauthOnuListPon
			Integer32,
		unauthOnuListOnuType
			Integer32,
		unauthOnuListSnLoid
			OCTET STRING,
		unauthOnuListPwd
			OCTET STRING,
		unauthOnuListMac
			OCTET STRING
	 }

-- 1.3.6.1.4.1.5875.800.3.11.1.1.1
unauthOnuListOnuIndex OBJECT-TYPE
	SYNTAX Integer32
	MAX-ACCESS read-only
	STATUS current
	DESCRIPTION
		"Column Description"
	::= { unauthOnuListEntry 1 }


-- 1.3.6.1.4.1.5875.800.3.11.1.1.2
unauthOnuListSlot OBJECT-TYPE
	SYNTAX Integer32
	MAX-ACCESS read-only
	STATUS current
	DESCRIPTION
		"Column Description"
	::= { unauthOnuListEntry 2 }


-- 1.3.6.1.4.1.5875.800.3.11.1.1.3
unauthOnuListPon OBJECT-TYPE
	SYNTAX Integer32
	MAX-ACCESS read-only
	STATUS current
	DESCRIPTION
		"Column Description"
	::= { unauthOnuListEntry 3 }


-- 1.3.6.1.4.1.5875.800.3.11.1.1.4
unauthOnuListOnuType OBJECT-TYPE
	SYNTAX Integer32
	MAX-ACCESS read-only
	STATUS current
	DESCRIPTION
		"Column Description"
	::= { unauthOnuListEntry 4 }


-- 1.3.6.1.4.1.5875.800.3.11.1.1.5
unauthOnuListSnLoid OBJECT-TYPE
	SYNTAX OCTET STRING
	MAX-ACCESS read-only
	STATUS current
	DESCRIPTION
		"Column Description"
	::= { unauthOnuListEntry 5 }


-- 1.3.6.1.4.1.5875.800.3.11.1.1.6
unauthOnuListPwd OBJECT-TYPE
	SYNTAX OCTET STRING
	MAX-ACCESS read-only
	STATUS current
	DESCRIPTION
		"Column Description"
	::= { unauthOnuListEntry 6 }


-- 1.3.6.1.4.1.5875.800.3.11.1.1.7
unauthOnuListMac OBJECT-TYPE
	SYNTAX OCTET STRING
	MAX-ACCESS read-only
	STATUS current
	DESCRIPTION
		"Column Description"
	::= { unauthOnuListEntry 7 }


-- 1.3.6.1.4.1.5875.800.3.12
onuAuthModeFor5116 OBJECT IDENTIFIER ::= { oltData 12 }


-- 1.3.6.1.4.1.5875.800.3.12.1
onuAuthModeTable OBJECT-TYPE
	SYNTAX SEQUENCE OF OnuAuthModeEntry
	MAX-ACCESS not-accessible
	STATUS current
	DESCRIPTION
		"Description"
	::= { onuAuthModeFor5116 1 }


-- 1.3.6.1.4.1.5875.800.3.12.1.1
onuAuthModeEntry OBJECT-TYPE
	SYNTAX OnuAuthModeEntry
	MAX-ACCESS not-accessible
	STATUS current
	DESCRIPTION
		"Row Description"
	INDEX { slotIndex }
	::= { onuAuthModeTable 1 }


OnuAuthModeEntry ::=
	SEQUENCE { 
		macAuthEnable
			TruthValue,
		snAuthEnable
			TruthValue
	 }

-- 1.3.6.1.4.1.5875.800.3.12.1.1.2
macAuthEnable OBJECT-TYPE
	SYNTAX TruthValue
	MAX-ACCESS read-write
	STATUS current
	DESCRIPTION
		"Column Description"
	::= { onuAuthModeEntry 2 }


-- 1.3.6.1.4.1.5875.800.3.12.1.1.3
snAuthEnable OBJECT-TYPE
	SYNTAX TruthValue
	MAX-ACCESS read-write
	STATUS current
	DESCRIPTION
		"Column Description"
	::= { onuAuthModeEntry 3 }


-- 1.3.6.1.4.1.5875.800.3.13
onuWarrantTypeFor5116 OBJECT IDENTIFIER ::= { oltData 13 }


-- 1.3.6.1.4.1.5875.800.3.13.1
onuWarrentTypeTable OBJECT-TYPE
	SYNTAX SEQUENCE OF OnuWarrentTypeEntry
	MAX-ACCESS not-accessible
	STATUS current
	DESCRIPTION
		"Description"
	::= { onuWarrantTypeFor5116 1 }


-- 1.3.6.1.4.1.5875.800.3.13.1.1
onuWarrentTypeEntry OBJECT-TYPE
	SYNTAX OnuWarrentTypeEntry
	MAX-ACCESS not-accessible
	STATUS current
	DESCRIPTION
		"Row Description"
	INDEX { slotIndex }
	::= { onuWarrentTypeTable 1 }


OnuWarrentTypeEntry ::=
	SEQUENCE { 
		warrantType
			Integer32
	 }

-- 1.3.6.1.4.1.5875.800.3.13.1.1.2
warrantType OBJECT-TYPE
	SYNTAX Integer32
	MAX-ACCESS read-write
	STATUS current
	DESCRIPTION
		"Column Description"
	::= { onuWarrentTypeEntry 2 }


-- 1.3.6.1.4.1.5875.800.3.14
ponAuthModeFor5516 OBJECT IDENTIFIER ::= { oltData 14 }


-- 1.3.6.1.4.1.5875.800.3.14.1
ponAuthModeTable OBJECT-TYPE
	SYNTAX SEQUENCE OF PonAuthModeEntry
	MAX-ACCESS not-accessible
	STATUS current
	DESCRIPTION
		"Description"
	::= { ponAuthModeFor5516 1 }


-- 1.3.6.1.4.1.5875.800.3.14.1.1
ponAuthModeEntry OBJECT-TYPE
	SYNTAX PonAuthModeEntry
	MAX-ACCESS not-accessible
	STATUS current
	DESCRIPTION
		"Row Description"
	INDEX { ponIndex }
	::= { ponAuthModeTable 1 }


PonAuthModeEntry ::=
	SEQUENCE { 
		authMode
			Integer32
	 }

-- 1.3.6.1.4.1.5875.800.3.14.1.1.2
authMode OBJECT-TYPE
	SYNTAX Integer32 (0..8)
	MAX-ACCESS read-write
	STATUS current
	DESCRIPTION
		"Column Description:
		0:Physical Markup authentication
		1:Physical Markup +Physical password authentication
		2:Physical password authentication
		3:Logic Markup +Logic password authentication
		4:Physical Markup /Logic Markup(include password)mix authentication
		5:unauthentication
		6:Logic Markup authentication(except password)
		7:Physical Markup /Logic Markup(except password)mix authentication
		8:Logic password authentication"
	::= { ponAuthModeEntry 2 }


-- 1.3.6.1.4.1.5875.800.3.15
cardWarrentFor5516 OBJECT IDENTIFIER ::= { oltData 15 }


-- 1.3.6.1.4.1.5875.800.3.15.1
cardWarrentTable OBJECT-TYPE
	SYNTAX SEQUENCE OF CardWarrentEntry
	MAX-ACCESS not-accessible
	STATUS current
	DESCRIPTION
		"Description"
	::= { cardWarrentFor5516 1 }


-- 1.3.6.1.4.1.5875.800.3.15.1.1
cardWarrentEntry OBJECT-TYPE
	SYNTAX CardWarrentEntry
	MAX-ACCESS not-accessible
	STATUS current
	DESCRIPTION
		"Row Description"
	INDEX { slotIndex }
	::= { cardWarrentTable 1 }


CardWarrentEntry ::=
	SEQUENCE { 
		warrentCardType
			Integer32
	 }

-- 1.3.6.1.4.1.5875.800.3.15.1.1.2
warrentCardType OBJECT-TYPE
	SYNTAX Integer32
	MAX-ACCESS read-write
	STATUS current
	DESCRIPTION
		"Column Description"
	::= { cardWarrentEntry 2 }


-- 1.3.6.1.4.1.5875.800.3.16
globalVlan OBJECT IDENTIFIER ::= { oltData 16 }


-- 1.3.6.1.4.1.5875.800.3.16.1
globalVlanTable OBJECT-TYPE
	SYNTAX SEQUENCE OF GlobalVlanEntry
	MAX-ACCESS not-accessible
	STATUS current
	DESCRIPTION
		"Description"
	::= { globalVlan 1 }


-- 1.3.6.1.4.1.5875.800.3.16.1.1
globalVlanEntry OBJECT-TYPE
	SYNTAX GlobalVlanEntry
	MAX-ACCESS not-accessible
	STATUS current
	DESCRIPTION
		"Row Description"
	INDEX { vlanConfigId }
	::= { globalVlanTable 1 }


GlobalVlanEntry ::=
	SEQUENCE { 
		vlanConfigId
			Integer32,
		serviceName
			OCTET STRING,
		beginVlanId
			Integer32,
		endVlanId
			Integer32,
		upLinkPort
			Integer32,
		tagStatus
			INTEGER,
		globalVlanAction
			INTEGER
	 }

-- 1.3.6.1.4.1.5875.800.3.16.1.1.1
vlanConfigId OBJECT-TYPE
	SYNTAX Integer32
	MAX-ACCESS read-only
	STATUS current
	DESCRIPTION
		"Column Description"
	::= { globalVlanEntry 1 }


-- 1.3.6.1.4.1.5875.800.3.16.1.1.2
serviceName OBJECT-TYPE
	SYNTAX OCTET STRING
	MAX-ACCESS read-write
	STATUS current
	DESCRIPTION
		"Column Description"
	::= { globalVlanEntry 2 }


-- 1.3.6.1.4.1.5875.800.3.16.1.1.3
beginVlanId OBJECT-TYPE
	SYNTAX Integer32 (-2147483648..2147483647)
	MAX-ACCESS read-write
	STATUS current
	DESCRIPTION
		"Column Description"
	::= { globalVlanEntry 3 }


-- 1.3.6.1.4.1.5875.800.3.16.1.1.4
endVlanId OBJECT-TYPE
	SYNTAX Integer32
	MAX-ACCESS read-write
	STATUS current
	DESCRIPTION
		"Column Description"
	::= { globalVlanEntry 4 }


-- 1.3.6.1.4.1.5875.800.3.16.1.1.5
upLinkPort OBJECT-TYPE
	SYNTAX Integer32
	MAX-ACCESS read-write
	STATUS current
	DESCRIPTION
		"Column Description"
	::= { globalVlanEntry 5 }


-- 1.3.6.1.4.1.5875.800.3.16.1.1.6
tagStatus OBJECT-TYPE
	SYNTAX INTEGER
		{
		tag(1),
		untag(0)
		}
	MAX-ACCESS read-write
	STATUS current
	DESCRIPTION
		"Column Description:
		1:tag(1)
		2:untag(0)"
	::= { globalVlanEntry 6 }


-- 1.3.6.1.4.1.5875.800.3.16.1.1.7
globalVlanAction OBJECT-TYPE
	SYNTAX INTEGER
		{
		active(1),
		create(4),
		destroy(6),
		modify(7)
		}
	MAX-ACCESS read-create
	STATUS current
	DESCRIPTION
		"Column Description"
	::= { globalVlanEntry 7 }


-- 1.3.6.1.4.1.5875.800.3.16.2
nextGlobalVlanId OBJECT-TYPE
	SYNTAX Integer32 (-2147483648..2147483647)
	MAX-ACCESS read-only
	STATUS current
	DESCRIPTION
		"Description"
	::= { globalVlan 2 }


-- 1.3.6.1.4.1.5875.800.3.17
onuManageVlan OBJECT IDENTIFIER ::= { oltData 17 }


-- 1.3.6.1.4.1.5875.800.3.17.1
onuManageVlanTable OBJECT-TYPE
	SYNTAX SEQUENCE OF OnuManageVlanEntry
	MAX-ACCESS not-accessible
	STATUS current
	DESCRIPTION
		"Description"
	::= { onuManageVlan 1 }


-- 1.3.6.1.4.1.5875.800.3.17.1.1
onuManageVlanEntry OBJECT-TYPE
	SYNTAX OnuManageVlanEntry
	MAX-ACCESS not-accessible
	STATUS current
	DESCRIPTION
		"Row Description"
	INDEX { onuIndex , manageVlanIndex }
	::= { onuManageVlanTable 1 }


OnuManageVlanEntry ::=
	SEQUENCE { 
		manageVlanIndex
			Integer32,			
		onuMac
			MacAddress,
		manageVlanName
			OCTET STRING,
		portNo
			Integer32,
		tagStatus1
			Integer32,
		manageSvlan
			Integer32,
		manageSvlanCos
			Integer32,
		mamageCvlan
			Integer32,
		mamageCvlanCos
			Integer32,
		onuIp
			IpAddress,
		onuMask
			IpAddress,
		onuGateway
			IpAddress,
		onuManageVlanAction
			INTEGER
	 }

-- 1.3.6.1.4.1.5875.800.3.17.1.1.2
manageVlanIndex OBJECT-TYPE
	SYNTAX Integer32
	MAX-ACCESS not-accessible
	STATUS current
	DESCRIPTION
		"Column Description"
	::= { onuManageVlanEntry 1 }		

onuMac OBJECT-TYPE
	SYNTAX MacAddress
	MAX-ACCESS read-write
	STATUS current
	DESCRIPTION
		"Column Description"
	::= { onuManageVlanEntry 2 }


-- 1.3.6.1.4.1.5875.800.3.17.1.1.4
manageVlanName OBJECT-TYPE
	SYNTAX OCTET STRING
	MAX-ACCESS read-write
	STATUS current
	DESCRIPTION
		"Column Description"
	::= { onuManageVlanEntry 4 }


-- 1.3.6.1.4.1.5875.800.3.17.1.1.5
portNo OBJECT-TYPE
	SYNTAX Integer32
	MAX-ACCESS read-write
	STATUS current
	DESCRIPTION
		"Column Description"
	::= { onuManageVlanEntry 5 }


-- 1.3.6.1.4.1.5875.800.3.17.1.1.6
tagStatus1 OBJECT-TYPE
	SYNTAX Integer32
	MAX-ACCESS read-write
	STATUS current
	DESCRIPTION
		"Column Description"
	::= { onuManageVlanEntry 6 }


-- 1.3.6.1.4.1.5875.800.3.17.1.1.7
manageSvlan OBJECT-TYPE
	SYNTAX Integer32
	MAX-ACCESS read-write
	STATUS current
	DESCRIPTION
		"Column Description"
	::= { onuManageVlanEntry 7 }


-- 1.3.6.1.4.1.5875.800.3.17.1.1.8
manageSvlanCos OBJECT-TYPE
	SYNTAX Integer32
	MAX-ACCESS read-write
	STATUS current
	DESCRIPTION
		"Column Description"
	::= { onuManageVlanEntry 8 }


-- 1.3.6.1.4.1.5875.800.3.17.1.1.9
mamageCvlan OBJECT-TYPE
	SYNTAX Integer32
	MAX-ACCESS read-write
	STATUS current
	DESCRIPTION
		"Column Description"
	::= { onuManageVlanEntry 9 }


-- 1.3.6.1.4.1.5875.800.3.17.1.1.10
mamageCvlanCos OBJECT-TYPE
	SYNTAX Integer32
	MAX-ACCESS read-write
	STATUS current
	DESCRIPTION
		"Column Description"
	::= { onuManageVlanEntry 10 }


-- 1.3.6.1.4.1.5875.800.3.17.1.1.11
onuIp OBJECT-TYPE
	SYNTAX IpAddress
	MAX-ACCESS read-write
	STATUS current
	DESCRIPTION
		"Column Description"
	::= { onuManageVlanEntry 11 }


-- 1.3.6.1.4.1.5875.800.3.17.1.1.12
onuMask OBJECT-TYPE
	SYNTAX IpAddress
	MAX-ACCESS read-write
	STATUS current
	DESCRIPTION
		"Column Description"
	::= { onuManageVlanEntry 12 }


-- 1.3.6.1.4.1.5875.800.3.17.1.1.13
onuGateway OBJECT-TYPE
	SYNTAX IpAddress
	MAX-ACCESS read-write
	STATUS current
	DESCRIPTION
		"Column Description"
	::= { onuManageVlanEntry 13 }


-- 1.3.6.1.4.1.5875.800.3.17.1.1.14
onuManageVlanAction OBJECT-TYPE
	SYNTAX INTEGER { modify(7) }
	MAX-ACCESS read-create
	STATUS current
	DESCRIPTION
		"Column Description"
	::= { onuManageVlanEntry 14 }


-- 1.3.6.1.4.1.5875.800.3.18
trunkConfig OBJECT IDENTIFIER ::= { oltData 18 }


-- 1.3.6.1.4.1.5875.800.3.18.1
trunkConfigTable OBJECT-TYPE
	SYNTAX SEQUENCE OF TrunkConfigEntry
	MAX-ACCESS not-accessible
	STATUS current
	DESCRIPTION
		"Description"
	::= { trunkConfig 1 }


-- 1.3.6.1.4.1.5875.800.3.18.1.1
trunkConfigEntry OBJECT-TYPE
	SYNTAX TrunkConfigEntry
	MAX-ACCESS not-accessible
	STATUS current
	DESCRIPTION
		"Row Description"
	INDEX { trunkGroupId }
	::= { trunkConfigTable 1 }


TrunkConfigEntry ::=
	SEQUENCE { 
		trunkGroupId
			Integer32,
		masterPort
			Integer32,
		memberPort
			Integer32,
		trunkConfigAction
			INTEGER
	 }

-- 1.3.6.1.4.1.5875.800.3.18.1.1.1
trunkGroupId OBJECT-TYPE
	SYNTAX Integer32
	MAX-ACCESS read-only
	STATUS current
	DESCRIPTION
		"Column Description"
	::= { trunkConfigEntry 1 }


-- 1.3.6.1.4.1.5875.800.3.18.1.1.2
masterPort OBJECT-TYPE
	SYNTAX Integer32
	MAX-ACCESS read-write
	STATUS current
	DESCRIPTION
		"Column Description"
	::= { trunkConfigEntry 2 }


-- 1.3.6.1.4.1.5875.800.3.18.1.1.3
memberPort OBJECT-TYPE
	SYNTAX Integer32
	MAX-ACCESS read-write
	STATUS current
	DESCRIPTION
		"ctp,<<=127; ?nit +?Xb 1-7;"
	::= { trunkConfigEntry 3 }


-- 1.3.6.1.4.1.5875.800.3.18.1.1.4
trunkConfigAction OBJECT-TYPE
	SYNTAX INTEGER
		{
		active(1),
		create(4),
		destroy(6),
		modify(7)
		}
	MAX-ACCESS read-create
	STATUS current
	DESCRIPTION
		"Column Description"
	::= { trunkConfigEntry 4 }


-- 1.3.6.1.4.1.5875.800.3.18.2
nextTrunkConfigId OBJECT-TYPE
	SYNTAX Integer32 (-2147483648..2147483647)
	MAX-ACCESS read-only
	STATUS current
	DESCRIPTION
		"Description"
	::= { trunkConfig 2 }


-- 1.3.6.1.4.1.5875.800.3.19
onuPonConfig OBJECT IDENTIFIER ::= { oltData 19 }


-- 1.3.6.1.4.1.5875.800.3.19.1
onuPonCfgTable OBJECT-TYPE
	SYNTAX SEQUENCE OF OnuPonCfgEntry
	MAX-ACCESS not-accessible
	STATUS current
	DESCRIPTION
		"Description"
	::= { onuPonConfig 1 }


-- 1.3.6.1.4.1.5875.800.3.19.1.1
onuPonCfgEntry OBJECT-TYPE
	SYNTAX OnuPonCfgEntry
	MAX-ACCESS not-accessible
	STATUS current
	DESCRIPTION
		"Row Description"
	INDEX { onuIndex }
	::= { onuPonCfgTable 1 }


OnuPonCfgEntry ::=
	SEQUENCE { 
		upBandwidth
			Integer32,
		dnBandwidth
			Integer32,
		upAssureBandwidth
			Integer32,
		upFixedBandwidth
			Integer32,
		onuPonCfgActon
			Integer32
	 }

-- 1.3.6.1.4.1.5875.800.3.19.1.1.1
upBandwidth OBJECT-TYPE
	SYNTAX Integer32
	MAX-ACCESS read-write
	STATUS current
	DESCRIPTION
		"Column Description"
	::= { onuPonCfgEntry 1 }


-- 1.3.6.1.4.1.5875.800.3.19.1.1.2
dnBandwidth OBJECT-TYPE
	SYNTAX Integer32
	MAX-ACCESS read-write
	STATUS current
	DESCRIPTION
		"Column Description"
	::= { onuPonCfgEntry 2 }


-- 1.3.6.1.4.1.5875.800.3.19.1.1.3
upAssureBandwidth OBJECT-TYPE
	SYNTAX Integer32
	MAX-ACCESS read-write
	STATUS current
	DESCRIPTION
		"Description"
	::= { onuPonCfgEntry 3 }


-- 1.3.6.1.4.1.5875.800.3.19.1.1.4
upFixedBandwidth OBJECT-TYPE
	SYNTAX Integer32
	MAX-ACCESS read-write
	STATUS current
	DESCRIPTION
		"Description"
	::= { onuPonCfgEntry 4 }


-- 1.3.6.1.4.1.5875.800.3.19.1.1.5
onuPonCfgActon OBJECT-TYPE
	SYNTAX Integer32
	MAX-ACCESS read-create
	STATUS current
	DESCRIPTION
		"Description"
	::= { onuPonCfgEntry 5 }


-- 1.3.6.1.4.1.5875.800.3.20
saveCfg2Flash OBJECT IDENTIFIER ::= { oltData 20 }


-- 1.3.6.1.4.1.5875.800.3.20.1
save2Flash OBJECT-TYPE
	SYNTAX Integer32
	MAX-ACCESS read-write
	STATUS current
	DESCRIPTION
		"Description"
	::= { saveCfg2Flash 1 }


-- 1.3.6.1.4.1.5875.800.3.21
mac2OnuInfo OBJECT IDENTIFIER ::= { oltData 21 }


-- 1.3.6.1.4.1.5875.800.3.21.1
mac2OnuInfoTable OBJECT-TYPE
	SYNTAX SEQUENCE OF Mac2OnuInfoEntry
	MAX-ACCESS not-accessible
	STATUS current
	DESCRIPTION
		"Description"
	::= { mac2OnuInfo 1 }


-- 1.3.6.1.4.1.5875.800.3.21.1.1
mac2OnuInfoEntry OBJECT-TYPE
	SYNTAX Mac2OnuInfoEntry
	MAX-ACCESS not-accessible
	STATUS current
	DESCRIPTION
		"Row Description"
	INDEX { onuMacString }
	::= { mac2OnuInfoTable 1 }


Mac2OnuInfoEntry ::=
	SEQUENCE { 
		onuMacString
			OCTET STRING,
		onuAuthID
			Integer32,
		onuWhileListID
			Integer32
	 }

-- 1.3.6.1.4.1.5875.800.3.21.1.1.1
onuMacString OBJECT-TYPE
	SYNTAX OCTET STRING (SIZE (12))
	MAX-ACCESS not-accessible
	STATUS current
	DESCRIPTION
		"Column Description"
	::= { mac2OnuInfoEntry 1 }


-- 1.3.6.1.4.1.5875.800.3.21.1.1.2
onuAuthID OBJECT-TYPE
	SYNTAX Integer32
	MAX-ACCESS read-only
	STATUS current
	DESCRIPTION
		"Column Description"
	::= { mac2OnuInfoEntry 2 }


-- 1.3.6.1.4.1.5875.800.3.21.1.1.3
onuWhileListID OBJECT-TYPE
	SYNTAX Integer32
	MAX-ACCESS read-only
	STATUS current
	DESCRIPTION
		"Column Description"
	::= { mac2OnuInfoEntry 3 }


-- 1.3.6.1.4.1.5875.800.3.22
sn2OnuInfo OBJECT IDENTIFIER ::= { oltData 22 }


-- 1.3.6.1.4.1.5875.800.3.22.1
sn2OnuInfoTable OBJECT-TYPE
	SYNTAX SEQUENCE OF Sn2OnuInfoEntry
	MAX-ACCESS not-accessible
	STATUS current
	DESCRIPTION
		"Description"
	::= { sn2OnuInfo 1 }


-- 1.3.6.1.4.1.5875.800.3.22.1.1
sn2OnuInfoEntry OBJECT-TYPE
	SYNTAX Sn2OnuInfoEntry
	MAX-ACCESS not-accessible
	STATUS current
	DESCRIPTION
		"Row Description"
	INDEX { onuSNString }
	::= { sn2OnuInfoTable 1 }


Sn2OnuInfoEntry ::=
	SEQUENCE { 
		onuSNString
			OCTET STRING,
		onuSNAuthID
			Integer32,
		onuSNWhilteListID
			Integer32
	 }

-- 1.3.6.1.4.1.5875.800.3.22.1.1.1
onuSNString OBJECT-TYPE
	SYNTAX OCTET STRING (SIZE (1..24))
	MAX-ACCESS not-accessible
	STATUS current
	DESCRIPTION
		"Column Description"
	::= { sn2OnuInfoEntry 1 }


-- 1.3.6.1.4.1.5875.800.3.22.1.1.2
onuSNAuthID OBJECT-TYPE
	SYNTAX Integer32
	MAX-ACCESS read-only
	STATUS current
	DESCRIPTION
		"Column Description"
	::= { sn2OnuInfoEntry 2 }


-- 1.3.6.1.4.1.5875.800.3.22.1.1.3
onuSNWhilteListID OBJECT-TYPE
	SYNTAX Integer32
	MAX-ACCESS read-only
	STATUS current
	DESCRIPTION
		"Column Description"
	::= { sn2OnuInfoEntry 3 }


-- 1.3.6.1.4.1.5875.800.3.23
snmpConfig OBJECT IDENTIFIER ::= { oltData 23 }


-- 1.3.6.1.4.1.5875.800.3.23.1
trapReceiveIp OBJECT-TYPE
	SYNTAX OCTET STRING
	MAX-ACCESS read-write
	STATUS current
	DESCRIPTION
		"Description"
	::= { snmpConfig 1 }


-- 1.3.6.1.4.1.5875.800.3.23.2
community OBJECT-TYPE
	SYNTAX OCTET STRING
	MAX-ACCESS read-write
	STATUS current
	DESCRIPTION
		"Description"
	::= { snmpConfig 2 }

snmpTrapTable	OBJECT-TYPE
	SYNTAX		SEQUENCE  OF  SnmpTrapEntry
	MAX-ACCESS	not-accessible
	STATUS		current
	DESCRIPTION	"Description"
	::=  { snmpConfig  3 }

snmpTrapEntry	OBJECT-TYPE
	SYNTAX		SnmpTrapEntry
	MAX-ACCESS	not-accessible
	STATUS		current
	DESCRIPTION	"Row Description"
	INDEX		{  snmpTrapIndex  }
	::=  { snmpTrapTable 1 }

SnmpTrapEntry  ::=  SEQUENCE {
	snmpTrapIndex  Integer32,
	snmpTrapIpv4  IpAddress,
	snmpTrapPort  Integer32,
	snmpTrapVersion  INTEGER,
	snmpTrapReportVersion  INTEGER,
	snmpTrapCommunity  OCTET STRING,
	snmpTrapAction  INTEGER
	}


snmpTrapIndex	OBJECT-TYPE	
	SYNTAX			Integer32
	MAX-ACCESS		not-accessible
	STATUS			current
	DESCRIPTION		"Column Description"
	::=  {  snmpTrapEntry  1  }


snmpTrapIpv4	OBJECT-TYPE	
	SYNTAX			IpAddress
	MAX-ACCESS		read-write
	STATUS			current
	DESCRIPTION		"Column Description"
	::=  {  snmpTrapEntry  2  }


snmpTrapPort	OBJECT-TYPE	
	SYNTAX			Integer32
	MAX-ACCESS		read-write
	STATUS			current
	DESCRIPTION		"Column Description"
	::=  {  snmpTrapEntry  3  }


snmpTrapVersion	OBJECT-TYPE	
	SYNTAX			INTEGER  { v1 ( 1 ) , v2c ( 2 ) } 
	MAX-ACCESS		read-write
	STATUS			current
	DESCRIPTION		"Column Description"
	::=  {  snmpTrapEntry  4  }


snmpTrapReportVersion	OBJECT-TYPE	
	SYNTAX			INTEGER  { privFormat ( 0 ) , stdFormat ( 1 ) } 
	MAX-ACCESS		read-write
	STATUS			current
	DESCRIPTION		"Column Description"
	::=  {  snmpTrapEntry  5  }


snmpTrapCommunity	OBJECT-TYPE	
	SYNTAX			OCTET STRING
	MAX-ACCESS		read-write
	STATUS			current
	DESCRIPTION		"Column Description"
	::=  {  snmpTrapEntry  6  }


snmpTrapAction	OBJECT-TYPE	
	SYNTAX			INTEGER  { create ( 4 ) , destroy ( 6 ) , modify ( 7 ) , active ( 1 ) } 
	MAX-ACCESS		read-write
	STATUS			current
	DESCRIPTION		"Column Description"
	::=  {  snmpTrapEntry  20  }

snmpCommunityTable	OBJECT-TYPE
	SYNTAX		SEQUENCE  OF  SnmpCommunityEntry
	MAX-ACCESS	not-accessible
	STATUS		current
	DESCRIPTION	"Description"
	::=  { snmpConfig  4 }

snmpCommunityEntry	OBJECT-TYPE
	SYNTAX		SnmpCommunityEntry
	MAX-ACCESS	not-accessible
	STATUS		current
	DESCRIPTION	"Row Description"
	INDEX		{  snmpCommunityIndex  }
	::=  { snmpCommunityTable 1 }

SnmpCommunityEntry  ::=  SEQUENCE {
	snmpCommunityIndex  Integer32,
	snmpCommunity  OCTET STRING,
	snmpCommunityPermission  INTEGER
	}


snmpCommunityIndex	OBJECT-TYPE	
	SYNTAX			Integer32
	MAX-ACCESS		not-accessible
	STATUS			current
	DESCRIPTION		"Column Description"
	::=  {  snmpCommunityEntry  1  }


snmpCommunity	OBJECT-TYPE	
	SYNTAX			OCTET STRING
	MAX-ACCESS		read-write
	STATUS			current
	DESCRIPTION		"Column Description"
	::=  {  snmpCommunityEntry  2  }


snmpCommunityPermission	OBJECT-TYPE	
	SYNTAX			INTEGER  { ro ( 1 ) , rw ( 2 ) } 
	MAX-ACCESS		read-write
	STATUS			current
	DESCRIPTION		"Column Description"
	::=  {  snmpCommunityEntry  3  }

	
-- 1.3.6.1.4.1.5875.800.3.24
igmpConfig OBJECT IDENTIFIER ::= { oltData 24 }

	
igmpBaseCfg	OBJECT IDENTIFIER
	::=  {  igmpConfig  1  }

igmpMode	OBJECT-TYPE	
	SYNTAX			INTEGER  { controlled ( 1 ) , proxy-proxy ( 2 ) , snooping ( 3 ) , proxy-snooping ( 4 ) , disable ( 5 ) , active ( 6 ) } 
	MAX-ACCESS		read-only
	STATUS			current
	DESCRIPTION		"Description"
	::=  {  igmpBaseCfg  1  }

igmpVlan	OBJECT-TYPE	
	SYNTAX			Integer32
	MAX-ACCESS		read-write
	STATUS			current
	DESCRIPTION		"Description"
	::=  {  igmpBaseCfg  2  }

igmpProxyIp	OBJECT-TYPE	
	SYNTAX			IpAddress
	MAX-ACCESS		read-write
	STATUS			current
	DESCRIPTION		"Description"
	::=  {  igmpBaseCfg  3  }

igmpProtocolVersion	OBJECT-TYPE	
	SYNTAX			INTEGER  { igmpv1v2 ( 1 ) , igmpv3 ( 2 ) } 
	MAX-ACCESS		read-only
	STATUS			current
	DESCRIPTION		"Description"
	::=  {  igmpBaseCfg  4  }

igmpProtocolPara	OBJECT IDENTIFIER
	::=  {  igmpConfig  2  }

robustnessVariable	OBJECT-TYPE	
	SYNTAX			Integer32
	MAX-ACCESS		read-write
	STATUS			current
	DESCRIPTION		"Description"
	::=  {  igmpProtocolPara  1  }

queryRespInterval	OBJECT-TYPE	
	SYNTAX			Integer32
	MAX-ACCESS		read-write
	STATUS			current
	DESCRIPTION		"Description"
	::=  {  igmpProtocolPara  2  }

lastQueryInterval	OBJECT-TYPE	
	SYNTAX			Integer32
	MAX-ACCESS		read-write
	STATUS			current
	DESCRIPTION		"Description"
	::=  {  igmpProtocolPara  3  }

lastQueryCount	OBJECT-TYPE	
	SYNTAX			Integer32
	MAX-ACCESS		read-write
	STATUS			current
	DESCRIPTION		"Description"
	::=  {  igmpProtocolPara  4  }

queryInterval	OBJECT-TYPE	
	SYNTAX			Integer32
	MAX-ACCESS		read-write
	STATUS			current
	DESCRIPTION		"Description"
	::=  {  igmpProtocolPara  5  }

groupMembInterval	OBJECT-TYPE	
	SYNTAX			Integer32  ( -2147483648 .. 2147483647  ) 
	MAX-ACCESS		read-write
	STATUS			current
	DESCRIPTION		"Description"
	::=  {  igmpProtocolPara  6  }


igmpProfileTable	OBJECT-TYPE
	SYNTAX		SEQUENCE  OF  IgmpProfileEntry
	MAX-ACCESS	not-accessible
	STATUS		current
	DESCRIPTION	"Description"
	::=  { igmpConfig  4 }

igmpProfileEntry	OBJECT-TYPE
	SYNTAX		IgmpProfileEntry
	MAX-ACCESS	not-accessible
	STATUS		current
	DESCRIPTION	"Row Description"
	INDEX		{  igmpProfileIndex  }
	::=  { igmpProfileTable 1 }

IgmpProfileEntry  ::=  SEQUENCE {
	igmpProfileIndex  Integer32,
	igmpProfileName  OCTET STRING,
	igmpProfileAction  INTEGER
	}


igmpProfileIndex	OBJECT-TYPE	
	SYNTAX			Integer32
	MAX-ACCESS		not-accessible
	STATUS			current
	DESCRIPTION		"Column Description"
	::=  {  igmpProfileEntry  1  }


igmpProfileName	OBJECT-TYPE	
	SYNTAX			OCTET STRING
	MAX-ACCESS		read-write
	STATUS			current
	DESCRIPTION		"Column Description"
	::=  {  igmpProfileEntry  2  }


igmpProfileAction	OBJECT-TYPE	
	SYNTAX			INTEGER  { active ( 1 ) , create ( 4 ) , destroy ( 6 ) , modify ( 7 ) } 
	MAX-ACCESS		read-write
	STATUS			current
	DESCRIPTION		"Column Description"
	::=  {  igmpProfileEntry  20  }

igmpProfileGroupTable	OBJECT-TYPE
	SYNTAX		SEQUENCE  OF  IgmpProfileGroupEntry
	MAX-ACCESS	not-accessible
	STATUS		current
	DESCRIPTION	"Description"
	::=  { igmpConfig  5 }

igmpProfileGroupEntry	OBJECT-TYPE
	SYNTAX		IgmpProfileGroupEntry
	MAX-ACCESS	not-accessible
	STATUS		current
	DESCRIPTION	"Row Description"
	INDEX		{  igmpProfileIndex, igmpProfileGroupIndex  }
	::=  { igmpProfileGroupTable 1 }

IgmpProfileGroupEntry  ::=  SEQUENCE {
	igmpProfileGroupIndex  Integer32,
	groupAddressBegin  IpAddress,
	groupAddressEnd  IpAddress,
	igmpProfileGroupAuthority  INTEGER,
	igmpProfileGroupAction  INTEGER
	}


igmpProfileGroupIndex	OBJECT-TYPE	
	SYNTAX			Integer32
	MAX-ACCESS		not-accessible
	STATUS			current
	DESCRIPTION		"Column Description"
	::=  {  igmpProfileGroupEntry  1  }


groupAddressBegin	OBJECT-TYPE	
	SYNTAX			IpAddress
	MAX-ACCESS		read-write
	STATUS			current
	DESCRIPTION		"Column Description"
	::=  {  igmpProfileGroupEntry  2  }


groupAddressEnd	OBJECT-TYPE	
	SYNTAX			IpAddress
	MAX-ACCESS		read-write
	STATUS			current
	DESCRIPTION		"Column Description"
	::=  {  igmpProfileGroupEntry  3  }


igmpProfileGroupAuthority	OBJECT-TYPE	
	SYNTAX			INTEGER  { normal ( 1 ) , preview ( 2 ) , forbid ( 3 ) } 
	MAX-ACCESS		read-write
	STATUS			current
	DESCRIPTION		"Column Description"
	::=  {  igmpProfileGroupEntry  4  }


igmpProfileGroupAction	OBJECT-TYPE	
	SYNTAX			INTEGER  { active ( 1 ) , create ( 4 ) , destroy ( 6 ) , modify ( 7 ) } 
	MAX-ACCESS		read-write
	STATUS			current
	DESCRIPTION		"Column Description"
	::=  {  igmpProfileGroupEntry  20  }

igmpActiveMultiGroupNumberTable	OBJECT-TYPE
	SYNTAX		SEQUENCE  OF  IgmpActiveMultiGroupNumberEntry
	MAX-ACCESS	not-accessible
	STATUS		current
	DESCRIPTION	"Description"
	::=  { igmpConfig  6 }

igmpActiveMultiGroupNumberEntry	OBJECT-TYPE
	SYNTAX		IgmpActiveMultiGroupNumberEntry
	MAX-ACCESS	not-accessible
	STATUS		current
	DESCRIPTION	"Row Description"
	INDEX		{  portIndex, igmpvlan  }
	::=  { igmpActiveMultiGroupNumberTable 1 }

IgmpActiveMultiGroupNumberEntry  ::=  SEQUENCE {
	igmpvlan  Integer32,
	igmpActiveMultiGroup  Integer32
	}


igmpvlan	OBJECT-TYPE	
	SYNTAX			Integer32
	MAX-ACCESS		not-accessible
	STATUS			current
	DESCRIPTION		"Column Description"
	::=  {  igmpActiveMultiGroupNumberEntry  1  }


igmpActiveMultiGroup	OBJECT-TYPE	
	SYNTAX			Integer32
	MAX-ACCESS		read-only
	STATUS			current
	DESCRIPTION		"Column Description"
	::=  {  igmpActiveMultiGroupNumberEntry  2  }

igmpactiveJoinPortsNumberTable	OBJECT-TYPE
	SYNTAX		SEQUENCE  OF  IgmpactiveJoinPortsNumberEntry
	MAX-ACCESS	not-accessible
	STATUS		current
	DESCRIPTION	"Description"
	::=  { igmpConfig  7 }

igmpactiveJoinPortsNumberEntry	OBJECT-TYPE
	SYNTAX		IgmpactiveJoinPortsNumberEntry
	MAX-ACCESS	not-accessible
	STATUS		current
	DESCRIPTION	"Row Description"
	INDEX		{  fttbIfIndex, igmpMultiGroupAddress  }
	::=  { igmpactiveJoinPortsNumberTable 1 }

IgmpactiveJoinPortsNumberEntry  ::=  SEQUENCE {
	igmpMultiGroupAddress  IpAddress,
	activeJoinPorts  Integer32
	}


igmpMultiGroupAddress	OBJECT-TYPE	
	SYNTAX			IpAddress
	MAX-ACCESS		not-accessible
	STATUS			current
	DESCRIPTION		"Column Description"
	::=  {  igmpactiveJoinPortsNumberEntry  1  }


activeJoinPorts	OBJECT-TYPE	
	SYNTAX			Integer32
	MAX-ACCESS		read-only
	STATUS			current
	DESCRIPTION		"Column Description"
	::=  {  igmpactiveJoinPortsNumberEntry  2  }

portIgmpCfgTable	OBJECT-TYPE
	SYNTAX		SEQUENCE  OF  PortIgmpCfgEntry
	MAX-ACCESS	not-accessible
	STATUS		current
	DESCRIPTION	"Description"
	::=  { igmpConfig  8 }

portIgmpCfgEntry	OBJECT-TYPE
	SYNTAX		PortIgmpCfgEntry
	MAX-ACCESS	not-accessible
	STATUS		current
	DESCRIPTION	"Row Description"
	INDEX		{  portIndex, profileIndex  }
	::=  { portIgmpCfgTable 1 }

PortIgmpCfgEntry  ::=  SEQUENCE {
	profileIndex  Integer32,
	portCtrlEnable  INTEGER,
	igmpProfile  OCTET STRING,
	leaveMode  INTEGER,
	maxOnlineNum  Integer32,
	portBandwidth  Integer32,
	portSignalVlan  Integer32,
	portIgmpCfgAction  RowStatus
	}


profileIndex	OBJECT-TYPE	
	SYNTAX			Integer32  ( -2147483648 .. 2147483647  ) 
	MAX-ACCESS		not-accessible
	STATUS			current
	DESCRIPTION		"Description"
	::=  {  portIgmpCfgEntry  1  }


portCtrlEnable	OBJECT-TYPE	
	SYNTAX			INTEGER  { controlled ( 1 ) , uncontrolled ( 0 ) } 
	MAX-ACCESS		read-write
	STATUS			current
	DESCRIPTION		"Column Description"
	::=  {  portIgmpCfgEntry  2  }


igmpProfile	OBJECT-TYPE	
	SYNTAX			OCTET STRING
	MAX-ACCESS		read-write
	STATUS			current
	DESCRIPTION		"Column Description"
	::=  {  portIgmpCfgEntry  3  }


leaveMode	OBJECT-TYPE	
	SYNTAX			INTEGER  { nonFastLeave ( 0 ) , fastLeave ( 1 ) } 
	MAX-ACCESS		read-write
	STATUS			current
	DESCRIPTION		"Column Description"
	::=  {  portIgmpCfgEntry  4  }


maxOnlineNum	OBJECT-TYPE	
	SYNTAX			Integer32  ( -2147483648 .. 2147483647  ) 
	MAX-ACCESS		read-write
	STATUS			current
	DESCRIPTION		"Column Description"
	::=  {  portIgmpCfgEntry  5  }


portBandwidth	OBJECT-TYPE	
	SYNTAX			Integer32  ( -2147483648 .. 2147483647  ) 
	MAX-ACCESS		read-write
	STATUS			current
	DESCRIPTION		"Column Description"
	::=  {  portIgmpCfgEntry  6  }


portSignalVlan	OBJECT-TYPE	
	SYNTAX			Integer32  ( -2147483648 .. 2147483647  ) 
	MAX-ACCESS		read-write
	STATUS			current
	DESCRIPTION		"Column Description"
	::=  {  portIgmpCfgEntry  7  }


portIgmpCfgAction	OBJECT-TYPE	
	SYNTAX			RowStatus  { active ( 1 ) , notInService ( 2 ) , notReady ( 3 ) , createAndGo ( 4 ) , createAndWait ( 5 ) , destroy ( 6 ) } 
	MAX-ACCESS		read-create
	STATUS			current
	DESCRIPTION		"Column Description"
	::=  {  portIgmpCfgEntry  20  }

		
-- 1.3.6.1.4.1.5875.800.3.25
onuAuth OBJECT IDENTIFIER ::= { oltData 25 }


-- 1.3.6.1.4.1.5875.800.3.25.1
onuPhysicsAuthTable OBJECT-TYPE
	SYNTAX SEQUENCE OF OnuPhysicsAuthEntry
	MAX-ACCESS not-accessible
	STATUS current
	DESCRIPTION
		"Description"
	::= { onuAuth 1 }


-- 1.3.6.1.4.1.5875.800.3.25.1.1
onuPhysicsAuthEntry OBJECT-TYPE
	SYNTAX OnuPhysicsAuthEntry
	MAX-ACCESS not-accessible
	STATUS current
	DESCRIPTION
		"Row Description"
	INDEX { onuIndex }
	::= { onuPhysicsAuthTable 1 }


OnuPhysicsAuthEntry ::=
	SEQUENCE { 
		onuSlotForMacAuth
			Integer32,
		onuPonForMacAuth
			Integer32,
		onuNoForMacAuth
			Integer32,
		onuTypeForMacAuth
			Integer32,
		macForMacAuth
			OCTET STRING,
		passwordForMacAuth
			OCTET STRING,
		actionForMacAuth
			INTEGER
	 }

-- 1.3.6.1.4.1.5875.800.3.25.1.1.1
onuSlotForMacAuth OBJECT-TYPE
	SYNTAX Integer32
	MAX-ACCESS read-write
	STATUS current
	DESCRIPTION
		"Column Description"
	::= { onuPhysicsAuthEntry 1 }


-- 1.3.6.1.4.1.5875.800.3.25.1.1.2
onuPonForMacAuth OBJECT-TYPE
	SYNTAX Integer32
	MAX-ACCESS read-write
	STATUS current
	DESCRIPTION
		"Column Description"
	::= { onuPhysicsAuthEntry 2 }


-- 1.3.6.1.4.1.5875.800.3.25.1.1.3
onuNoForMacAuth OBJECT-TYPE
	SYNTAX Integer32
	MAX-ACCESS read-write
	STATUS current
	DESCRIPTION
		"Column Description"
	::= { onuPhysicsAuthEntry 3 }


-- 1.3.6.1.4.1.5875.800.3.25.1.1.4
onuTypeForMacAuth OBJECT-TYPE
	SYNTAX Integer32
	MAX-ACCESS read-write
	STATUS current
	DESCRIPTION
		"Column Description"
	::= { onuPhysicsAuthEntry 4 }


-- 1.3.6.1.4.1.5875.800.3.25.1.1.5
macForMacAuth OBJECT-TYPE
	SYNTAX OCTET STRING
	MAX-ACCESS read-write
	STATUS current
	DESCRIPTION
		"Column Description"
	::= { onuPhysicsAuthEntry 5 }


-- 1.3.6.1.4.1.5875.800.3.25.1.1.6
passwordForMacAuth OBJECT-TYPE
	SYNTAX OCTET STRING (SIZE (1..6))
	MAX-ACCESS read-write
	STATUS current
	DESCRIPTION
		"Column Description"
	::= { onuPhysicsAuthEntry 6 }


-- 1.3.6.1.4.1.5875.800.3.25.1.1.17
actionForMacAuth OBJECT-TYPE
	SYNTAX INTEGER
		{
		active(1),
		create(4),
		destroy(6)
		}
	MAX-ACCESS read-write
	STATUS current
	DESCRIPTION
		"Column Description"
	::= { onuPhysicsAuthEntry 17 }


-- 1.3.6.1.4.1.5875.800.3.25.2
onuSnAuthFor5116Table OBJECT-TYPE
	SYNTAX SEQUENCE OF OnuSnAuthFor5116Entry
	MAX-ACCESS not-accessible
	STATUS current
	DESCRIPTION
		"Description"
	::= { onuAuth 2 }


-- 1.3.6.1.4.1.5875.800.3.25.2.1
onuSnAuthFor5116Entry OBJECT-TYPE
	SYNTAX OnuSnAuthFor5116Entry
	MAX-ACCESS not-accessible
	STATUS current
	DESCRIPTION
		"Row Description"
	INDEX { onuIndex }
	::= { onuSnAuthFor5116Table 1 }


OnuSnAuthFor5116Entry ::=
	SEQUENCE { 
		slotNoForSnAuth
			Integer32,
		ponNoForSnMacAuth
			Integer32,
		onuNoForSnAuth
			Integer32,
		onuTypeForSnAuth
			Integer32,
		snForsnAuth
			OCTET STRING,
		passwordForSnAuth
			OCTET STRING,
		actionForSnAuth
			INTEGER
	 }

-- 1.3.6.1.4.1.5875.800.3.25.2.1.1
slotNoForSnAuth OBJECT-TYPE
	SYNTAX Integer32
	MAX-ACCESS read-write
	STATUS current
	DESCRIPTION
		"Column Description"
	::= { onuSnAuthFor5116Entry 1 }


-- 1.3.6.1.4.1.5875.800.3.25.2.1.2
ponNoForSnMacAuth OBJECT-TYPE
	SYNTAX Integer32
	MAX-ACCESS read-write
	STATUS current
	DESCRIPTION
		"Column Description"
	::= { onuSnAuthFor5116Entry 2 }


-- 1.3.6.1.4.1.5875.800.3.25.2.1.3
onuNoForSnAuth OBJECT-TYPE
	SYNTAX Integer32
	MAX-ACCESS read-write
	STATUS current
	DESCRIPTION
		"Column Description"
	::= { onuSnAuthFor5116Entry 3 }


-- 1.3.6.1.4.1.5875.800.3.25.2.1.4
onuTypeForSnAuth OBJECT-TYPE
	SYNTAX Integer32
	MAX-ACCESS read-write
	STATUS current
	DESCRIPTION
		"Column Description"
	::= { onuSnAuthFor5116Entry 4 }


-- 1.3.6.1.4.1.5875.800.3.25.2.1.5
snForsnAuth OBJECT-TYPE
	SYNTAX OCTET STRING
	MAX-ACCESS read-write
	STATUS current
	DESCRIPTION
		"Column Description"
	::= { onuSnAuthFor5116Entry 5 }


-- 1.3.6.1.4.1.5875.800.3.25.2.1.6
passwordForSnAuth OBJECT-TYPE
	SYNTAX OCTET STRING
	MAX-ACCESS read-write
	STATUS current
	DESCRIPTION
		"Column Description"
	::= { onuSnAuthFor5116Entry 6 }


-- 1.3.6.1.4.1.5875.800.3.25.2.1.17
actionForSnAuth OBJECT-TYPE
	SYNTAX INTEGER
		{
		active(1),
		create(4),
		destroy(6)
		}
	MAX-ACCESS read-write
	STATUS current
	DESCRIPTION
		"Column Description :
		1:create(4)
		2:destroy(6)"
	::= { onuSnAuthFor5116Entry 17 }     
	
	
cvlan2Svlan	OBJECT IDENTIFIER
	::=  {  oltData  26  }
	
cvlan2SvlanTable	OBJECT-TYPE
	SYNTAX		SEQUENCE  OF  Cvlan2SvlanEntry
	MAX-ACCESS	not-accessible
	STATUS		current
	DESCRIPTION	"Description"
	::=  { cvlan2Svlan  1 }

cvlan2SvlanEntry	OBJECT-TYPE
	SYNTAX		Cvlan2SvlanEntry
	MAX-ACCESS	not-accessible
	STATUS		current
	DESCRIPTION	"Row Description"
	INDEX		{  onuIndex, onuCvlanVid  }
	::=  { cvlan2SvlanTable 1 }

Cvlan2SvlanEntry  ::=  SEQUENCE {
	onuCvlanVid  Integer32,
	onuSvlanVid  Integer32
	}


onuCvlanVid	OBJECT-TYPE	
	SYNTAX			Integer32
	MAX-ACCESS		not-accessible
	STATUS			current
	DESCRIPTION		"Column Description"
	::=  {  cvlan2SvlanEntry  1  }


onuSvlanVid	OBJECT-TYPE	
	SYNTAX			Integer32
	MAX-ACCESS		read-only
	STATUS			current
	DESCRIPTION		"Description"
	::=  {  cvlan2SvlanEntry  2  }

		
gponOnuServiceConfig	OBJECT IDENTIFIER
	::=  {  oltData  30  }			

	
-- 1.3.6.1.4.1.5875.800.3.50
gponConfig OBJECT IDENTIFIER ::= { oltData 50 }

gponRmtManageCfgTable	OBJECT-TYPE
	SYNTAX		SEQUENCE  OF  GponRmtManageCfgEntry
	MAX-ACCESS	not-accessible
	STATUS		current
	DESCRIPTION	"Description"
	::=  { gponOnuServiceConfig  1 }

gponRmtManageCfgEntry	OBJECT-TYPE
	SYNTAX		GponRmtManageCfgEntry
	MAX-ACCESS	not-accessible
	STATUS		current
	DESCRIPTION	"Row Description"
	INDEX		{  onuIndex  }
	::=  { gponRmtManageCfgTable 1 }

GponRmtManageCfgEntry  ::=  SEQUENCE {
	gponRmtManageUrl  OCTET STRING,
	gponRmtManageUser  OCTET STRING,
	gponRmtManagePwd  OCTET STRING,
	gponRmtManageAction  INTEGER
	}


gponRmtManageUrl	OBJECT-TYPE	
	SYNTAX			OCTET STRING
	MAX-ACCESS		read-write
	STATUS			current
	DESCRIPTION		"Column Description"
	::=  {  gponRmtManageCfgEntry  1  }


gponRmtManageUser	OBJECT-TYPE	
	SYNTAX			OCTET STRING
	MAX-ACCESS		read-write
	STATUS			current
	DESCRIPTION		"Column Description"
	::=  {  gponRmtManageCfgEntry  2  }


gponRmtManagePwd	OBJECT-TYPE	
	SYNTAX			OCTET STRING
	MAX-ACCESS		read-write
	STATUS			current
	DESCRIPTION		"Column Description"
	::=  {  gponRmtManageCfgEntry  3  }


gponRmtManageAction	OBJECT-TYPE	
	SYNTAX			INTEGER  { active ( 1 ) , create ( 4 ) , modify ( 7 ) } 
	MAX-ACCESS		read-create
	STATUS			current
	DESCRIPTION		"Description"
	::=  {  gponRmtManageCfgEntry  4  }

gponVEIPManagePathCfgTable	OBJECT-TYPE
	SYNTAX		SEQUENCE  OF  GponVEIPManagePathCfgEntry
	MAX-ACCESS	not-accessible
	STATUS		current
	DESCRIPTION	"Description"
	::=  { gponOnuServiceConfig  2 }

gponVEIPManagePathCfgEntry	OBJECT-TYPE
	SYNTAX		GponVEIPManagePathCfgEntry
	MAX-ACCESS	not-accessible
	STATUS		current
	DESCRIPTION	"Row Description"
	INDEX		{  portIndex  }
	::=  { gponVEIPManagePathCfgTable 1 }

GponVEIPManagePathCfgEntry  ::=  SEQUENCE {
	gponVEIPManagePathDsp  Integer32,
	gponVEIPManagePathIPAddress  OCTET STRING,   
	gponVEIPManagePathIpMask  Integer32,
	gponVEIPManagePathGateWay  OCTET STRING,
	gponVEIPManagePathPrimaryDns  OCTET STRING,
	gponVEIPManagePathSecondaryDns  OCTET STRING,
	gponVEIPManagePathNetworkPort  Integer32,
	gponVEIPManagePathCVlan  Integer32,
	gponVEIPManagePathCVlanCos  Integer32,   
	gponVEIPManagePathAction  INTEGER
	}


gponVEIPManagePathDsp	OBJECT-TYPE	
	SYNTAX			Integer32  ( 0 .. 1  ) 
	MAX-ACCESS		read-write
	STATUS			current
	DESCRIPTION		"Column Description"
	::=  {  gponVEIPManagePathCfgEntry  1  }


gponVEIPManagePathIPAddress	OBJECT-TYPE	
	SYNTAX			OCTET STRING
	MAX-ACCESS		read-write
	STATUS			current
	DESCRIPTION		"Column Description"
	::=  {  gponVEIPManagePathCfgEntry  2  }


gponVEIPManagePathGateWay	OBJECT-TYPE	
	SYNTAX			OCTET STRING
	MAX-ACCESS		read-write
	STATUS			current
	DESCRIPTION		"Column Description"
	::=  {  gponVEIPManagePathCfgEntry  3  }


gponVEIPManagePathPrimaryDns	OBJECT-TYPE	
	SYNTAX			OCTET STRING
	MAX-ACCESS		read-write
	STATUS			current
	DESCRIPTION		"Column Description"
	::=  {  gponVEIPManagePathCfgEntry  4  }


gponVEIPManagePathSecondaryDns	OBJECT-TYPE	
	SYNTAX			OCTET STRING
	MAX-ACCESS		read-write
	STATUS			current
	DESCRIPTION		"Description"
	::=  {  gponVEIPManagePathCfgEntry  5  }


gponVEIPManagePathNetworkPort	OBJECT-TYPE	
	SYNTAX			Integer32  ( 0 .. 65535  ) 
	MAX-ACCESS		read-write
	STATUS			current
	DESCRIPTION		"Column Description"
	::=  {  gponVEIPManagePathCfgEntry  6  }


gponVEIPManagePathCVlan	OBJECT-TYPE	
	SYNTAX			Integer32  ( 1 .. 4085 | 65535  ) 
	MAX-ACCESS		read-write
	STATUS			current
	DESCRIPTION		"Column Description"
	::=  {  gponVEIPManagePathCfgEntry  7  }


gponVEIPManagePathCVlanCos	OBJECT-TYPE	
	SYNTAX			Integer32  ( 0 .. 7 | 65535  ) 
	MAX-ACCESS		read-write
	STATUS			current
	DESCRIPTION		"Column Description"
	::=  {  gponVEIPManagePathCfgEntry  8  }
	
gponVEIPManagePathIpMask	OBJECT-TYPE	
	SYNTAX			Integer32  
	MAX-ACCESS		read-write
	STATUS			current
	DESCRIPTION		"Column Description"
	::=  {  gponVEIPManagePathCfgEntry  9  }
	      
gponVEIPManagePathAction	OBJECT-TYPE	
	SYNTAX			INTEGER  { active ( 1 ) , create ( 4 ) , destroy ( 6 ) , modify ( 7 ) } 
	MAX-ACCESS		read-create
	STATUS			current
	DESCRIPTION		"Description"
	::=  {  gponVEIPManagePathCfgEntry  30  }

gponVEIPServiceCfgTable	OBJECT-TYPE
	SYNTAX		SEQUENCE  OF  GponVEIPServiceCfgEntry
	MAX-ACCESS	not-accessible
	STATUS		current
	DESCRIPTION	"Description"
	::=  { gponOnuServiceConfig  3 }

gponVEIPServiceCfgEntry	OBJECT-TYPE
	SYNTAX		GponVEIPServiceCfgEntry
	MAX-ACCESS	not-accessible
	STATUS		current
	DESCRIPTION	"Row Description"
	INDEX		{  portIndex, gponVEIPServiceID  }
	::=  { gponVEIPServiceCfgTable 1 }

GponVEIPServiceCfgEntry  ::=  SEQUENCE {
	gponVEIPServiceID  Integer32,
	gponVEIPServiceTls  Integer32,
	gponVEIPServiceCVlan  Integer32,
	gponVEIPServiceCVlanCos  Integer32,
	gponVEIPServiceTVlan  Integer32,
	gponVEIPServiceTVlanCos  Integer32,
	gponVEIPServiceSVlan  Integer32,
	gponVEIPServiceSVlanCos  Integer32,
	gponVEIPServiceUsBandWidth  Integer32,
	gponVEIPServiceDsBandWidth  Integer32,
	gponVEIPServiceProfileName  OCTET STRING,
	gponVEIPServiceAction  INTEGER
	}


gponVEIPServiceID	OBJECT-TYPE	
	SYNTAX			Integer32
	MAX-ACCESS		not-accessible
	STATUS			current
	DESCRIPTION		"Column Description"
	::=  {  gponVEIPServiceCfgEntry  1  }


gponVEIPServiceTls	OBJECT-TYPE	
	SYNTAX			Integer32  ( 0 .. 1  ) 
	MAX-ACCESS		read-write
	STATUS			current
	DESCRIPTION		"Column Description"
	::=  {  gponVEIPServiceCfgEntry  2  }


gponVEIPServiceCVlan	OBJECT-TYPE	
	SYNTAX			Integer32  ( 1 .. 4085 | 65535  ) 
	MAX-ACCESS		read-write
	STATUS			current
	DESCRIPTION		"Column Description"
	::=  {  gponVEIPServiceCfgEntry  3  }


gponVEIPServiceCVlanCos	OBJECT-TYPE	
	SYNTAX			Integer32  ( 0 .. 7 | 65535  ) 
	MAX-ACCESS		read-write
	STATUS			current
	DESCRIPTION		"Column Description"
	::=  {  gponVEIPServiceCfgEntry  4  }


gponVEIPServiceTVlan	OBJECT-TYPE	
	SYNTAX			Integer32  ( 1 .. 4085 | 65535  ) 
	MAX-ACCESS		read-write
	STATUS			current
	DESCRIPTION		"Column Description"
	::=  {  gponVEIPServiceCfgEntry  5  }


gponVEIPServiceTVlanCos	OBJECT-TYPE	
	SYNTAX			Integer32  ( 0 .. 7 | 65535  ) 
	MAX-ACCESS		read-write
	STATUS			current
	DESCRIPTION		"Column Description"
	::=  {  gponVEIPServiceCfgEntry  6  }


gponVEIPServiceSVlan	OBJECT-TYPE	
	SYNTAX			Integer32  ( 1 .. 4085 | 65535  ) 
	MAX-ACCESS		read-write
	STATUS			current
	DESCRIPTION		"Column Description"
	::=  {  gponVEIPServiceCfgEntry  7  }


gponVEIPServiceSVlanCos	OBJECT-TYPE	
	SYNTAX			Integer32  ( 0 .. 7 | 65535  ) 
	MAX-ACCESS		read-write
	STATUS			current
	DESCRIPTION		"Column Description"
	::=  {  gponVEIPServiceCfgEntry  8  }


gponVEIPServiceUsBandWidth	OBJECT-TYPE	
	SYNTAX			Integer32
	MAX-ACCESS		read-write
	STATUS			current
	DESCRIPTION		"Column Description"
	::=  {  gponVEIPServiceCfgEntry  9  }


gponVEIPServiceDsBandWidth	OBJECT-TYPE	
	SYNTAX			Integer32  ( -2147483648 .. 2147483647  ) 
	MAX-ACCESS		read-write
	STATUS			current
	DESCRIPTION		"Column Description"
	::=  {  gponVEIPServiceCfgEntry  10  }


gponVEIPServiceProfileName	OBJECT-TYPE	
	SYNTAX			OCTET STRING
	MAX-ACCESS		read-write
	STATUS			current
	DESCRIPTION		"Column Description"
	::=  {  gponVEIPServiceCfgEntry  11  }


gponVEIPServiceAction	OBJECT-TYPE	
	SYNTAX			INTEGER  { active ( 1 ) , create ( 4 ) , destroy ( 6 ) , modify ( 7 ) } 
	MAX-ACCESS		read-create
	STATUS			current
	DESCRIPTION		"Column Description"
	::=  {  gponVEIPServiceCfgEntry  12  }
	
	
gponVEIPServiceIDCfgTable	OBJECT-TYPE
	SYNTAX		SEQUENCE  OF  GponVEIPServiceIDCfgEntry
	MAX-ACCESS	not-accessible
	STATUS		current
	DESCRIPTION	"Description"
	::=  { gponOnuServiceConfig  4 }

gponVEIPServiceIDCfgEntry	OBJECT-TYPE
	SYNTAX		GponVEIPServiceIDCfgEntry
	MAX-ACCESS	not-accessible
	STATUS		current
	DESCRIPTION	"Row Description"
	INDEX		{  portIndex  }
	::=  { gponVEIPServiceIDCfgTable 1 }

GponVEIPServiceIDCfgEntry  ::=  SEQUENCE {
	nextGponVEIPServiceID  Integer32
	}
	
nextGponVEIPServiceID OBJECT-TYPE
	SYNTAX Integer32
	MAX-ACCESS read-only
	STATUS current
	DESCRIPTION
		"Column Description"
	::= { gponVEIPServiceIDCfgEntry 1 }
		
		
-- 1.3.6.1.4.1.5875.800.3.50.1
gponServiceBandwidthCfg OBJECT IDENTIFIER ::= { gponConfig 1 }


-- 1.3.6.1.4.1.5875.800.3.50.1.1
gponServiceBandwidthCfgTable OBJECT-TYPE
	SYNTAX SEQUENCE OF GponServiceBandwidthCfgEntry
	MAX-ACCESS not-accessible
	STATUS current
	DESCRIPTION
		"Description"
	::= { gponServiceBandwidthCfg 1 }


-- 1.3.6.1.4.1.5875.800.3.50.1.1.1
gponServiceBandwidthCfgEntry OBJECT-TYPE
	SYNTAX GponServiceBandwidthCfgEntry
	MAX-ACCESS not-accessible
	STATUS current
	DESCRIPTION
		"Row Description"
	INDEX { onuIndex, gponServiceType }
	::= { gponServiceBandwidthCfgTable 1 }


GponServiceBandwidthCfgEntry ::=
	SEQUENCE { 
		gponServiceType
			Integer32,
		gponFixedBandwidth
			Integer32,
		gponAssureBandwidth
			Integer32,
		gponMaxBandwidth
			Integer32,
		gponBandwidthCfgAction
			RowStatus
	 }

-- 1.3.6.1.4.1.5875.800.3.50.1.1.1.1
gponServiceType OBJECT-TYPE
	SYNTAX Integer32
	MAX-ACCESS not-accessible
	STATUS current
	DESCRIPTION
		"Column Description:
		1:IGMP 
		2:broadband Internet access
		3:Voice
		4:TDM
		5:integrated service"
	::= { gponServiceBandwidthCfgEntry 1 }


-- 1.3.6.1.4.1.5875.800.3.50.1.1.1.2
gponFixedBandwidth OBJECT-TYPE
	SYNTAX Integer32 (-2147483648..2147483647)
	MAX-ACCESS read-write
	STATUS current
	DESCRIPTION
		"Column Description"
	::= { gponServiceBandwidthCfgEntry 2 }


-- 1.3.6.1.4.1.5875.800.3.50.1.1.1.3
gponAssureBandwidth OBJECT-TYPE
	SYNTAX Integer32
	MAX-ACCESS read-write
	STATUS current
	DESCRIPTION
		"Column Description"
	::= { gponServiceBandwidthCfgEntry 3 }


-- 1.3.6.1.4.1.5875.800.3.50.1.1.1.4
gponMaxBandwidth OBJECT-TYPE
	SYNTAX Integer32
	MAX-ACCESS read-write
	STATUS current
	DESCRIPTION
		"Column Description"
	::= { gponServiceBandwidthCfgEntry 4 }


-- 1.3.6.1.4.1.5875.800.3.50.1.1.1.10
gponBandwidthCfgAction OBJECT-TYPE
	SYNTAX RowStatus
	MAX-ACCESS read-create
	STATUS current
	DESCRIPTION
		"Column Description"
	::= { gponServiceBandwidthCfgEntry 10 }

alarmStatus	OBJECT IDENTIFIER
	::=  {  oltData  60  }
	
powerAlarmStatusTable	OBJECT-TYPE
	SYNTAX		SEQUENCE  OF  PowerAlarmStatusEntry
	MAX-ACCESS	not-accessible
	STATUS		current
	DESCRIPTION	"Description"
	::=  { alarmStatus  1 }

powerAlarmStatusEntry	OBJECT-TYPE
	SYNTAX		PowerAlarmStatusEntry
	MAX-ACCESS	not-accessible
	STATUS		current
	DESCRIPTION	"Row Description"
	INDEX		{  powerIndex  }
	::=  { powerAlarmStatusTable 1 }

PowerAlarmStatusEntry  ::=  SEQUENCE {
	powerIndex  Integer32,
	powerAlarmStatus  INTEGER
	}


powerIndex	OBJECT-TYPE	
	SYNTAX			Integer32
	MAX-ACCESS		not-accessible
	STATUS			current
	DESCRIPTION		"Column Description"
	::=  {  powerAlarmStatusEntry  1  }


powerAlarmStatus	OBJECT-TYPE	
	SYNTAX			INTEGER  { normal ( 1 ) , lowVoltage ( 2 ) , fault ( 3 ) } 
	MAX-ACCESS		read-only
	STATUS			current
	DESCRIPTION		"Column Description"
	::=  {  powerAlarmStatusEntry  2  }

fanAlarmStatusTable	OBJECT-TYPE
	SYNTAX		SEQUENCE  OF  FanAlarmStatusEntry
	MAX-ACCESS	not-accessible
	STATUS		current
	DESCRIPTION	"Description"
	::=  { alarmStatus  2 }

fanAlarmStatusEntry	OBJECT-TYPE
	SYNTAX		FanAlarmStatusEntry
	MAX-ACCESS	not-accessible
	STATUS		current
	DESCRIPTION	"Row Description"
	INDEX		{  slotIndex  }
	::=  { fanAlarmStatusTable 1 }

FanAlarmStatusEntry  ::=  SEQUENCE {
	fanAlarmStatus  INTEGER
	}

fanAlarmStatus	OBJECT-TYPE	
	SYNTAX			INTEGER  { normal ( 1 ) , stop ( 2 ) , abnormity ( 3 ) , nonChecking ( 4 ) } 
	MAX-ACCESS		read-only
	STATUS			current
	DESCRIPTION		"Column Description"
	::=  {  fanAlarmStatusEntry  1  }	
	

currentAlarmTable	OBJECT-TYPE
	SYNTAX		SEQUENCE  OF  CurrentAlarmEntry
	MAX-ACCESS	not-accessible
	STATUS		current
	DESCRIPTION	"Description"
	::=  { alarmStatus  3 }

currentAlarmEntry	OBJECT-TYPE
	SYNTAX		CurrentAlarmEntry
	MAX-ACCESS	not-accessible
	STATUS		current
	DESCRIPTION	"Row Description"
	INDEX		{  currentAlarmIndex  }
	::=  { currentAlarmTable 1 }

CurrentAlarmEntry  ::=  SEQUENCE {
	currentAlarmIndex  Integer32,
	currentAlarmCode  Integer32,
	currentAlarmIfIndex  Integer32,
	currentAlarmStatus  Integer32,
	currentAlarmStatusFlag  Integer32,
	currentAlarmBeginTime  DateAndTime,
	currentAlarmEndTime  DateAndTime,
	currentAlarmType  Integer32,
	currentAlarmAdditionalText  OCTET STRING
	}


currentAlarmIndex	OBJECT-TYPE	
	SYNTAX			Integer32
	MAX-ACCESS		not-accessible
	STATUS			current
	DESCRIPTION		"Column Description"
	::=  {  currentAlarmEntry  1  }


currentAlarmCode	OBJECT-TYPE	
	SYNTAX			Integer32
	MAX-ACCESS		read-only
	STATUS			current
	DESCRIPTION		"Column Description"
	::=  {  currentAlarmEntry  2  }


currentAlarmIfIndex	OBJECT-TYPE	
	SYNTAX			Integer32
	MAX-ACCESS		read-only
	STATUS			current
	DESCRIPTION		"Column Description"
	::=  {  currentAlarmEntry  3  }


currentAlarmStatus	OBJECT-TYPE	
	SYNTAX			Integer32
	MAX-ACCESS		read-only
	STATUS			current
	DESCRIPTION		"Column Description"
	::=  {  currentAlarmEntry  4  }


currentAlarmStatusFlag	OBJECT-TYPE	
	SYNTAX			Integer32
	MAX-ACCESS		read-only
	STATUS			current
	DESCRIPTION		"Column Description"
	::=  {  currentAlarmEntry  5  }


currentAlarmBeginTime	OBJECT-TYPE	
	SYNTAX			DateAndTime
	MAX-ACCESS		read-only
	STATUS			current
	DESCRIPTION		"Column Description"
	::=  {  currentAlarmEntry  6  }


currentAlarmEndTime	OBJECT-TYPE	
	SYNTAX			DateAndTime
	MAX-ACCESS		read-only
	STATUS			current
	DESCRIPTION		"Column Description"
	::=  {  currentAlarmEntry  7  }


currentAlarmType	OBJECT-TYPE	
	SYNTAX			Integer32
	MAX-ACCESS		read-only
	STATUS			current
	DESCRIPTION		"Column Description"
	::=  {  currentAlarmEntry  8  }


currentAlarmAdditionalText	OBJECT-TYPE	
	SYNTAX			OCTET STRING
	MAX-ACCESS		read-only
	STATUS			current
	DESCRIPTION		"Column Description"
	::=  {  currentAlarmEntry  9  }

hisAlarmTable	OBJECT-TYPE
	SYNTAX		SEQUENCE  OF  HisAlarmEntry
	MAX-ACCESS	not-accessible
	STATUS		current
	DESCRIPTION	"Description"
	::=  { alarmStatus  4 }

hisAlarmEntry	OBJECT-TYPE
	SYNTAX		HisAlarmEntry
	MAX-ACCESS	not-accessible
	STATUS		current
	DESCRIPTION	"Row Description"
	INDEX		{  hisAlarmIndex  }
	::=  { hisAlarmTable 1 }

HisAlarmEntry  ::=  SEQUENCE {
	hisAlarmIndex  Integer32,
	hisAlarmCode  Integer32,
	hisAlarmIfIndex  Integer32,
	hisAlarmStatus  Integer32,
	hisAlarmStatusFlag  Integer32,
	hisAlarmBeginTime  DateAndTime,
	hisAlarmEndTime  DateAndTime,
	hisAlarmType  Integer32,
	hisAlarmAdditionalText  OCTET STRING
	}


hisAlarmIndex	OBJECT-TYPE	
	SYNTAX			Integer32
	MAX-ACCESS		not-accessible
	STATUS			current
	DESCRIPTION		"Column Description"
	::=  {  hisAlarmEntry  1  }


hisAlarmCode	OBJECT-TYPE	
	SYNTAX			Integer32
	MAX-ACCESS		read-only
	STATUS			current
	DESCRIPTION		"Column Description"
	::=  {  hisAlarmEntry  2  }


hisAlarmIfIndex	OBJECT-TYPE	
	SYNTAX			Integer32
	MAX-ACCESS		read-only
	STATUS			current
	DESCRIPTION		"Column Description"
	::=  {  hisAlarmEntry  3  }


hisAlarmStatus	OBJECT-TYPE	
	SYNTAX			Integer32
	MAX-ACCESS		read-only
	STATUS			current
	DESCRIPTION		"Column Description"
	::=  {  hisAlarmEntry  4  }


hisAlarmStatusFlag	OBJECT-TYPE	
	SYNTAX			Integer32
	MAX-ACCESS		read-only
	STATUS			current
	DESCRIPTION		"Column Description"
	::=  {  hisAlarmEntry  5  }


hisAlarmBeginTime	OBJECT-TYPE	
	SYNTAX			DateAndTime
	MAX-ACCESS		read-only
	STATUS			current
	DESCRIPTION		"Column Description"
	::=  {  hisAlarmEntry  6  }


hisAlarmEndTime	OBJECT-TYPE	
	SYNTAX			DateAndTime
	MAX-ACCESS		read-only
	STATUS			current
	DESCRIPTION		"Column Description"
	::=  {  hisAlarmEntry  7  }


hisAlarmType	OBJECT-TYPE	
	SYNTAX			Integer32
	MAX-ACCESS		read-only
	STATUS			current
	DESCRIPTION		"Column Description"
	::=  {  hisAlarmEntry  8  }


hisAlarmAdditionalText	OBJECT-TYPE	
	SYNTAX			OCTET STRING
	MAX-ACCESS		read-only
	STATUS			current
	DESCRIPTION		"Column Description"
	::=  {  hisAlarmEntry  9  }

		
-- 1.3.6.1.4.1.5875.800.3.101
objectIndex OBJECT IDENTIFIER ::= { oltData 101 }


-- 1.3.6.1.4.1.5875.800.3.101.1
slotObjectIndexTable OBJECT-TYPE
	SYNTAX SEQUENCE OF SlotObjectIndexEntry
	MAX-ACCESS not-accessible
	STATUS current
	DESCRIPTION
		"Description"
	::= { objectIndex 1 }


-- 1.3.6.1.4.1.5875.800.3.101.1.1
slotObjectIndexEntry OBJECT-TYPE
	SYNTAX SlotObjectIndexEntry
	MAX-ACCESS not-accessible
	STATUS current
	DESCRIPTION
		"Row Description"
	INDEX { slotIndex }
	::= { slotObjectIndexTable 1 }


SlotObjectIndexEntry ::=
	SEQUENCE { 
		slotIndex
			Integer32
	 }

-- 1.3.6.1.4.1.5875.800.3.101.1.1.1
slotIndex OBJECT-TYPE
	SYNTAX Integer32
	MAX-ACCESS read-only
	STATUS current
	DESCRIPTION
		"Column Description"
	::= { slotObjectIndexEntry 1 }


-- 1.3.6.1.4.1.5875.800.3.101.2
onuObjectIndexTable OBJECT-TYPE
	SYNTAX SEQUENCE OF OnuObjectIndexEntry
	MAX-ACCESS not-accessible
	STATUS current
	DESCRIPTION
		"Description"
	::= { objectIndex 2 }


-- 1.3.6.1.4.1.5875.800.3.101.2.1
onuObjectIndexEntry OBJECT-TYPE
	SYNTAX OnuObjectIndexEntry
	MAX-ACCESS not-accessible
	STATUS current
	DESCRIPTION
		"Row Description"
	INDEX { onuIndex }
	::= { onuObjectIndexTable 1 }


OnuObjectIndexEntry ::=
	SEQUENCE { 
		onuIndex
			Unsigned32
	 }

-- 1.3.6.1.4.1.5875.800.3.101.2.1.1
onuIndex OBJECT-TYPE
	SYNTAX Unsigned32
	MAX-ACCESS read-only
	STATUS current
	DESCRIPTION
		"Column Description"
	::= { onuObjectIndexEntry 1 }


-- 1.3.6.1.4.1.5875.800.3.101.3
uplinkObjectIndexTable OBJECT-TYPE
	SYNTAX SEQUENCE OF UplinkObjectIndexEntry
	MAX-ACCESS not-accessible
	STATUS current
	DESCRIPTION
		"Description"
	::= { objectIndex 3 }


-- 1.3.6.1.4.1.5875.800.3.101.3.1
uplinkObjectIndexEntry OBJECT-TYPE
	SYNTAX UplinkObjectIndexEntry
	MAX-ACCESS not-accessible
	STATUS current
	DESCRIPTION
		"Row Description"
	INDEX { uplinkIndex }
	::= { uplinkObjectIndexTable 1 }


UplinkObjectIndexEntry ::=
	SEQUENCE { 
		uplinkIndex
			Unsigned32
	 }

-- 1.3.6.1.4.1.5875.800.3.101.3.1.1
uplinkIndex OBJECT-TYPE
	SYNTAX Unsigned32
	MAX-ACCESS read-only
	STATUS current
	DESCRIPTION
		"Column Description"
	::= { uplinkObjectIndexEntry 1 }


-- 1.3.6.1.4.1.5875.800.3.101.4
potsObjectIndexTable OBJECT-TYPE
	SYNTAX SEQUENCE OF PotsObjectIndexEntry
	MAX-ACCESS not-accessible
	STATUS current
	DESCRIPTION
		"Description"
	::= { objectIndex 4 }


-- 1.3.6.1.4.1.5875.800.3.101.4.1
potsObjectIndexEntry OBJECT-TYPE
	SYNTAX PotsObjectIndexEntry
	MAX-ACCESS not-accessible
	STATUS current
	DESCRIPTION
		"Row Description"
	INDEX { potsIndex }
	::= { potsObjectIndexTable 1 }


PotsObjectIndexEntry ::=
	SEQUENCE { 
		potsIndex
			Unsigned32
	 }

-- 1.3.6.1.4.1.5875.800.3.101.4.1.1
potsIndex OBJECT-TYPE
	SYNTAX Unsigned32
	MAX-ACCESS read-only
	STATUS current
	DESCRIPTION
		"Column Description"
	::= { potsObjectIndexEntry 1 }


-- 1.3.6.1.4.1.5875.800.3.101.5
portObjectIndexTable OBJECT-TYPE
	SYNTAX SEQUENCE OF PortObjectIndexEntry
	MAX-ACCESS not-accessible
	STATUS current
	DESCRIPTION
		"Description"
	::= { objectIndex 5 }


-- 1.3.6.1.4.1.5875.800.3.101.5.1
portObjectIndexEntry OBJECT-TYPE
	SYNTAX PortObjectIndexEntry
	MAX-ACCESS not-accessible
	STATUS current
	DESCRIPTION
		"Row Description"
	INDEX { portIndex }
	::= { portObjectIndexTable 1 }


PortObjectIndexEntry ::=
	SEQUENCE { 
		portIndex
			Unsigned32
	 }

-- 1.3.6.1.4.1.5875.800.3.101.5.1.1
portIndex OBJECT-TYPE
	SYNTAX Unsigned32
	MAX-ACCESS read-only
	STATUS current
	DESCRIPTION
		"Column Description"
	::= { portObjectIndexEntry 1 }


-- 1.3.6.1.4.1.5875.800.3.101.6
ponObjectIndexTable OBJECT-TYPE
	SYNTAX SEQUENCE OF PonObjectIndexEntry
	MAX-ACCESS not-accessible
	STATUS current
	DESCRIPTION
		"Description"
	::= { objectIndex 6 }


-- 1.3.6.1.4.1.5875.800.3.101.6.1
ponObjectIndexEntry OBJECT-TYPE
	SYNTAX PonObjectIndexEntry
	MAX-ACCESS not-accessible
	STATUS current
	DESCRIPTION
		"Row Description"
	INDEX { ponIndex }
	::= { ponObjectIndexTable 1 }


PonObjectIndexEntry ::=
	SEQUENCE { 
		ponIndex
			Unsigned32
	 }

-- 1.3.6.1.4.1.5875.800.3.101.6.1.1
ponIndex OBJECT-TYPE
	SYNTAX Unsigned32
	MAX-ACCESS read-only
	STATUS current
	DESCRIPTION
		"Column Description"
	::= { ponObjectIndexEntry 1 }


-- 1.3.6.1.4.1.5875.800.1001
equipTypeObjectId OBJECT IDENTIFIER ::= { standard 1001 }


-- 1.3.6.1.4.1.5875.800.1001.1
an5116v02 OBJECT-TYPE
	SYNTAX Integer32
	MAX-ACCESS read-only
	STATUS current
	DESCRIPTION
		"Description"
	::= { equipTypeObjectId 1 }


-- 1.3.6.1.4.1.5875.800.1001.2
an5116v06 OBJECT-TYPE
	SYNTAX Integer32
	MAX-ACCESS read-only
	STATUS current
	DESCRIPTION
		"Description"
	::= { equipTypeObjectId 2 }


-- 1.3.6.1.4.1.5875.800.1001.11
an5516v01 OBJECT-TYPE
	SYNTAX Integer32
	MAX-ACCESS read-only
	STATUS current
	DESCRIPTION
		"Description"
	::= { equipTypeObjectId 11 }
	
-- 1.3.6.1.4.1.5875.800.1001.12
an5516v04 OBJECT-TYPE
	SYNTAX Integer32
	MAX-ACCESS read-only
	STATUS current
	DESCRIPTION
		"Description"
	::= { equipTypeObjectId 12 }			
	

-- 1.3.6.1.4.1.5875.800.1001.14
GT5116-06B OBJECT-TYPE
	SYNTAX Integer32
	MAX-ACCESS read-only
	STATUS current
	DESCRIPTION
		"Description"
	::= { equipTypeObjectId 14 }


-- 1.3.6.1.4.1.5875.800.1001.21
an6016v01 OBJECT-TYPE
	SYNTAX Integer32
	MAX-ACCESS read-only
	STATUS current
	DESCRIPTION
		"Description"
	::= { equipTypeObjectId 21 }


-- 1.3.6.1.4.1.5875.800.1001.101
an2200v02 OBJECT-TYPE
	SYNTAX Integer32
	MAX-ACCESS read-only
	STATUS current
	DESCRIPTION
		"Description"
	::= { equipTypeObjectId 101 }


-- 1.3.6.1.4.1.5875.800.1001.111
an3300v02 OBJECT-TYPE
	SYNTAX Integer32
	MAX-ACCESS read-only
	STATUS current
	DESCRIPTION
		"Description"
	::= { equipTypeObjectId 111 }


-- 1.3.6.1.4.1.5875.800.1001.112
an3300v03 OBJECT-TYPE
	SYNTAX Integer32
	MAX-ACCESS read-only
	STATUS current
	DESCRIPTION
		"Description"
	::= { equipTypeObjectId 112 }


-- 1.3.6.1.4.1.5875.800.1001.121
an5006v15 OBJECT-TYPE
	SYNTAX Integer32
	MAX-ACCESS read-only
	STATUS current
	DESCRIPTION
		"Description"
	::= { equipTypeObjectId 121 }


-- 1.3.6.1.4.1.5875.800.1001.122
an5006v16 OBJECT-TYPE
	SYNTAX Integer32
	MAX-ACCESS read-only
	STATUS current
	DESCRIPTION
		"Description"
	::= { equipTypeObjectId 122 }


-- 1.3.6.1.4.1.5875.800.1001.131
an5006v20 OBJECT-TYPE
	SYNTAX Integer32
	MAX-ACCESS read-only
	STATUS current
	DESCRIPTION
		"Description"
	::= { equipTypeObjectId 131 }

		
	
END

--
-- GEPON-OLT-COMMON-MIB.my
--
